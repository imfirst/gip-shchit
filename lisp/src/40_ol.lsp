;;; ============================================================================
;;; Принципиальная однолинейная схема (листы А3, как в рабочем файле ГИП)
;;; ============================================================================
(setq *gip:KU* 49.907)
(setq *gip:C0* 3631.0 *gip:PITCH* 785.4)
(setq *gip:YB_L* -1348.267 *gip:YB_N* -1437.39 *gip:YB_PE* -1527.18 *gip:YB_LB* -1619.82)
(setq *gip:YDEV* -1996.65 *gip:YDB* -2614.5 *gip:YKN* -2751.8 *gip:YMG* -2989.8)
(setq *gip:YT* '(-4547.0 -5144.0 -5442.0 -5740.0 -7075.0))

(defun gip:short-type (tpl / t1 p)
  ;; "S201 C{I}" -> "S201"; "ВА47-29 1Р C{I}" -> "ВА47-29"
  (setq t1 tpl)
  (if (setq p (vl-string-search " C{I}" t1)) (setq t1 (substr t1 1 p)))
  (if (setq p (vl-string-search "C{I}" t1)) (setq t1 (substr t1 1 p)))
  (if (setq p (vl-string-search " {I}" t1)) (setq t1 (substr t1 1 p)))
  (setq t1 (gip:trim t1))
  (foreach suf '(" 1P+N" " 3P+N" " 1P" " 2P" " 3P" " 4P" " 1Р" " 2Р" " 3Р" " 4Р")
    (if (gip:ends t1 suf) (setq t1 (substr t1 1 (- (strlen t1) (strlen suf))))))
  (gip:trim t1))

(defun gip:brand-ser (b kind In / tpl st)
  (setq tpl (gip:g b kind))
  (cond ((null tpl) "")
        ((= (substr kind 1 1) "a") (setq st (gip:short-type tpl)) (if (= (gip:g b "name") "ABB") (strcat st "C") st))
        ((member kind '("dif" "dif4")) (gip:short-type tpl))
        (T (gip:fmt-model tpl In))))
(defun gip:rcd-ser (tpl / p t1)
  (setq t1 tpl)
  (if (setq p (vl-string-search "{I}" t1)) (setq t1 (substr t1 1 p)))
  (setq t1 (vl-string-right-trim "- " t1))
  (gip:short-type t1))

;; марка кабеля в узкой колонке схемы: без «(А)» и дефиса — «ВВГнгLS», «ППГнгHF»
(defun gip:mark-short (m) (gip:repl (gip:repl (gip:repl m "(А)" "") "(A)" "") "-" ""))
;; марка контактора -> две строки надписи: «ESB» + «25-40N», «КМ63-40М» + «25А», «NCH8» + «25/40»
(defun gip:km-split (m / p)
  (cond ((gip:starts m "ESB") (list "ESB" (substr m 4)))
        ((setq p (vl-string-search " " m)) (list (substr m 1 p) (gip:trim (substr m (+ p 2)))))
        ((setq p (vl-string-search "-" m)) (list (substr m 1 p) (substr m (+ p 2))))
        (T (list m ""))))
(defun gip:in-cable (In is3 / sq) (setq sq (cond ((<= In 25) 6) ((<= In 40) 10) (T 16))) (strcat "ВВГнгLS " (if is3 "5" "3") "x" (itoa sq)))
(defun gip:conduit (cab / sq p)
  (setq sq 2.5)
  (if (setq p (vl-string-search "×" cab)) (setq sq (atof (gip:repl (substr cab (+ p 2)) "," "."))))
  (cond ((<= sq 1.5) "П16") ((<= sq 2.5) "П20") ((<= sq 6.0) "П25") (T "П32")))
(defun gip:next-in (v lst / r) (setq r nil) (foreach x lst (if (and (null r) (> x v)) (setq r x))) (if r r (last lst)))

(defun gip:consumer (l / nm wet)
  (setq nm (gip:lower (gip:gn l "name" "")))
  (cond ((= (gip:g l "cat") "light") '("c_svet" -4352.0 -4224.0))
        ((= (gip:g l "cat") "floor") '("c_tp" -4381.0 -4311.0))
        ((or (member (gip:g l "cat") '("sock" "app")) (and (= (gip:g l "cat") "custom") (/= (gip:g l "poles") 3)))
         (if (= (gip:gn l "key" (gip:g l "id")) "oven")
           '("c_kab" -4311.0 -4311.0)
           (progn
             (setq wet (or (gip:has nm "сануз") (gip:has nm "ванн") (gip:has nm "душ") (gip:has nm "туалет") (gip:has nm "с/у")
                           (member (gip:gn l "key" (gip:g l "id")) '("wash" "dw" "dry"))))
             (if wet '("c_roz44" -4311.0 -4311.0) '("c_roz" -4311.0 -4311.0)))))
        (T '("c_kab" -4311.0 -4311.0))))

(defun gip:inom (l / cc) (setq cc (gip:cos l))
  (if (= (gip:g l "poles") 3) (/ (gip:g l "p") (* (sqrt 3.0) 0.4 cc)) (/ (gip:g l "p") (* 0.23 cc))))

;; видимость вставки "I" (элемент 10)
(defun gip:it-vis (it v) (if (and v (= (car it) "I") (nth 10 it)) (append (gip:take it 10) (list v) (gip:drop it 11)) it))
;; видимость блока «аппарат управления и защиты в РЩ» по числу полюсов
(defun gip:av-vis (n) (strcat "Автоматический выключатель " (nth (max 0 (min 3 (1- n))) '("однополюсный" "двухполюсный" "трехполюсный" "четырехполюсный"))))
(defun gip:rcd-vis (four) (if four "Дифференциальный выключатель четырехполюсный" "Дифференциальный выключатель двухполюсный"))
;; атрибуты аппарата на схеме
(defun gip:dev-atts (its d o)
  (mapcar '(lambda (it)
             (setq it (gip:it-vis it (gip:g o "vis")))
             (gip:it-atts it
               (append
                 (list (cons "НОМ.ТОК,А" (itoa (if (assoc "In" o) (cdr (assoc "In" o)) (gip:g d "In"))))
                       (cons "ПРОИЗВОДИТЕЛЬ" (if (assoc "maker" o) (cdr (assoc "maker" o)) (gip:g *gip:b* "name")))
                       (cons "СЕРИЯ" (gip:gn o "ser" ""))
                       (cons "НОМЕР" (if (assoc "ref" o) (cdr (assoc "ref" o)) (gip:gn d "ref" ""))))
                 (if (gip:g o "ma") (list (cons "IСР.,МА" (gip:g o "ma"))))
                 (if (gip:g o "type") (list (cons "ТИП" (gip:g o "type")))))))
          its))

;; колонки однолинейки и разбивка на листы по 19
(defun gip:ol-pages (B kup / cols nLO nLS pages cur i c need j CAP)
  (setq cols nil nLO 0 nLS 0 CAP 19)
  (foreach d (gip:g B "all")
    (cond ((= (gip:g d "kind") "rcd") (setq cols (cons (list '("t" . "rcd") (cons "d" d)) cols)))
          ((gip:g d "line")
           (cond ((gip:g (gip:g d "line") "num") (setq cols (cons (list '("t" . "line") (cons "d" d) (cons "no" (gip:g (gip:g d "line") "num"))) cols)))
                 ((= (gip:g (gip:g d "line") "cat") "light")
                  (setq nLO (1+ nLO) cols (cons (list '("t" . "line") (cons "d" d) (cons "no" (strcat "ЛО-" (itoa nLO)))) cols)))
                 (T (setq nLS (1+ nLS) cols (cons (list '("t" . "line") (cons "d" d) (cons "no" (strcat "ЛС-" (itoa nLS)))) cols)))))))
  (setq cols (reverse cols) pages nil cur nil i 0)
  (while (< i (length cols))
    (setq c (nth i cols) need 1)
    (if (= (gip:g c "t") "rcd")
      (progn (setq j (1+ i))
             (while (and (< j (length cols)) (= (gip:g (gip:g (nth j cols) "d") "feed") (gip:g (gip:g c "d") "id"))) (setq need (1+ need) j (1+ j)))))
    (if (and (> (+ (length cur) need) CAP) cur) (setq pages (append pages (list cur)) cur nil))
    (setq cur (append cur (list c)) i (1+ i)))
  (setq pages (append pages (list cur)))
  (if (and kup (>= (length (last pages)) CAP)) (setq pages (append pages (list nil))))
  pages)

;; ---------------------------------------------------------------- этажный щит
;; Настройки (поля fs* таблицы; пусто — авто). Селективность: автомат после счётчика — на ступень больше вводного
;; квартиры, УЗО — на ступень больше автомата, рубильник/автомат перед счётчиком — на ступень больше; при УЗО 100 мА
;; в квартире ток утечки в этажном щите — 300 мА.
(setq *gip:fs-brk* '(16 20 25 32 40 50 63 80 100 125) *gip:fs-qs* '(25 32 40 50 63 80 100 125) *gip:fs-rcd* '(25 40 63 80 100))
(defun gip:fs-int (S k) (if (numberp (gip:g S k)) (fix (gip:g S k))))
(defun gip:fs-str (S k) (if (and (= (type (gip:g S k)) 'STR) (/= (gip:trim (gip:g S k)) "")) (gip:trim (gip:g S k))))
(defun gip:sec-str (v) (if (equal v (fix v) 1e-9) (itoa (fix v)) (gip:repl (rtos v 2 1) "." ",")))
(defun gip:fs-cfg (S / is3 inA post postIn rcdIn idn pre preIn mark al sec)
  (setq is3 (= (gip:g S "phases") 3) inA (gip:gn S "inA" 40))
  (setq post (if (member (gip:g S "fsPost") '("av" "dif" "avrcd")) (gip:g S "fsPost") (if is3 "dif" "av")))
  (setq postIn (cond ((gip:fs-int S "fsPostIn")) (T (gip:next-in inA *gip:fs-brk*))))
  (setq rcdIn (if (= post "avrcd") (cond ((gip:fs-int S "fsRcdIn")) (T (gip:next-in postIn *gip:fs-rcd*)))))
  (setq idn (if (/= post "av") (cond ((gip:fs-int S "fsIdn")) ((gip:g S "fire") 300) (T 100))))
  (setq pre (if (= (gip:g S "fsPre") "qf") "qf" "qs"))
  (setq preIn (cond ((gip:fs-int S "fsPreIn")) (T (gip:next-in postIn (if (= pre "qs") *gip:fs-qs* *gip:fs-brk*)))))
  (setq mark (cond ((gip:fs-str S "fsMark")) ((gip:fs-str S "mark")) (T "ВВГнг(А)-LS")))
  (setq al (member (substr mark 1 1) '("А" "A")))
  (setq sec (cond ((numberp (gip:g S "fsCable")) (gip:g S "fsCable"))
                  (al (cond ((<= inA 40) 16) ((<= inA 63) 25) (T 35)))
                  (T (cond ((<= inA 25) 6) ((<= inA 40) 10) (T 16)))))
  (list (cons "post" post) (cons "postIn" postIn) (cons "rcdIn" rcdIn) (cons "idn" idn) (cons "pre" pre) (cons "preIn" preIn)
        (cons "meter" (cond ((gip:fs-str S "fsMeter")) (is3 "Меркурий 236 ART") (T "Меркурий 204 ARTMX2-02")))
        (cons "meterSpec" (cond ((gip:fs-str S "fsMeterSpec")) (is3 "400/230В 5-60А") (T "230В, 5-100А")))
        (cons "cable" (strcat mark " " (if is3 "5" "3") "x" (gip:sec-str sec)))))

;; оставляемые элементы прототипа (рамка, кабель с дугами, стояк, счётчик, PE) и детали аппаратов из floor3
(setq *gip:fs-keep* '(("floor3" 0 1 2 3 4 5 6 7 8 9 10 12 14 15 16 17 18 19 20 21 22 23 24 25 26 27 42 49 53)
                      ("floor1" 0 1 2 3 4 5 6 7 8 9 10 12 13 14 15 16 17 18 19 20 21 22 23 24 25 26 31 35 37)))
(setq *gip:fs-parts* '(("brk" "floor3" 5066.734974156 28 36 37 38 60 61 63 62)   ; автомат: нож L, контакт с крестом, расцепитель
                       ("brkN" "floor3" 5066.734974156 29 39 40 41 30 31)        ; второй полюс (N) автомата и связь ножей
                       ("rcdL" "floor3" 5066.734974156 28 36)                    ; полюс L УЗО
                       ("rcdN" "floor3" 5066.734974156 29 39 30 31)              ; полюс N УЗО и связь
                       ("diff" "floor3" 5066.734974156 32 33 34 35)              ; дифференциальный трансформатор
                       ("qs" "floor3" 6500.308914521 45 54 59)                   ; рубильник
                       ("sl3" "floor3" 5066.734974156 50 51 52) ("sl1" "floor3" 5066.734974156 51)
                       ("lbl1" "floor3" 6500.308914521 44)                       ; «QS 40А» над аппаратом перед счётчиком
                       ("lblQF" "floor1" 5066.734974156 49)                      ; «QF 50А» над автоматом после счётчика
                       ("lbl2a" "floor3" 5066.734974156 43) ("lbl2b" "floor3" 5066.734974156 13)))
(setq *gip:FS-LY* 1469.92215386 *gip:FS-NY* 1296.492577819 *gip:FS-BL* 216.787 *gip:FS-X* 4566.734974156)

(defun gip:fs-items (key x0 OX OY / p its)
  (setq p (assoc key *gip:fs-parts*) its (gip:proto (cadr p)))
  (mapcar '(lambda (i) (gip:shift-item (nth i its) (+ OX (- x0 (caddr p))) OY)) (cdddr p)))
(defun gip:fs-text (key x0 OX OY txt) (gip:emit (list (gip:it-text (car (gip:fs-items key x0 OX OY)) txt)) *gip:tag*))
;; аппарат: kind qs | qf | qfd | qd; x0 — начало ножа
(defun gip:fs-dev (kind x0 is3 OX OY / k)
  (foreach k (cond ((= kind "qs") '("qs")) ((= kind "qf") '("brk")) ((= kind "qfd") '("brk" "brkN" "diff")) (T '("rcdL" "rcdN" "diff")))
    (gip:emit (gip:fs-items k x0 OX OY) *gip:tag*))
  (gip:emit (gip:fs-items (if is3 "sl3" "sl1") x0 OX OY) *gip:tag*))
;; провод y от x1 до x2 с разрывами brk ((a b) ...)
(defun gip:fs-wire (y x1 x2 brk OX OY / tpl cur b)
  (setq tpl (nth 56 (gip:proto "floor3")) cur x1)
  (foreach b (gip:msort brk '(lambda (a c) (< (car a) (car c))))
    (if (> (car b) (+ cur 0.5)) (gip:emit (list (gip:it-poly tpl (list (+ OX cur) (+ OY y) (+ OX (car b)) (+ OY y)))) *gip:tag*))
    (setq cur (max cur (cadr b))))
  (if (> x2 (+ cur 0.5)) (gip:emit (list (gip:it-poly tpl (list (+ OX cur) (+ OY y) (+ OX x2) (+ OY y)))) *gip:tag*)))

(defun gip:floor-shield (S OX OY is3 / c name keep its it i p dm dq posts x0 kind brkL brkN pre lb)
  (setq c (gip:fs-cfg S) name (if is3 "floor3" "floor1") keep (cdr (assoc name *gip:fs-keep*)))
  ;; после счётчика: один аппарат на месте прототипа или автомат + УЗО (счётчик сдвигается вправо)
  ;; (счётчик и аппарат перед ним сдвигаются вправо, чтобы надписи не налезали)
  (if (= (gip:g c "post") "avrcd")
    (setq dm 300.0 dq 200.0 posts (list (list "qd" 4849.0) (list "qf" 5466.0)))
    (setq dm 0.0 dq 0.0 posts (list (list (if (= (gip:g c "post") "dif") "qfd" "qf") 5066.734974156))))
  (setq its (gip:proto name) lb nil)
  (foreach i keep
    (setq it (gip:shift-item (nth i its) OX OY))
    (cond ((= i 8) (setq it (gip:it-text it (gip:g c "cable"))))
          ((= i 12) (setq it (gip:it-att (gip:shift-item it dm 0.0) "СЕРИЯ" (gip:g c "meter"))))
          ((or (and is3 (= i 42)) (and (not is3) (= i 31))) (setq it (gip:it-text (gip:shift-item it dm 0.0) (gip:g c "meterSpec")))))
    (setq lb (cons it lb)))
  (gip:emit (reverse lb) *gip:tag*)
  ;; аппараты и надписи
  (setq brkL (list (list (+ 5783.521944339 dm) (+ 6000.308914521 dm))) brkN (list (list (+ 5783.521944339 dm) (+ 5997.145704499 dm))))
  (foreach p posts
    (setq kind (car p) x0 (cadr p))
    (gip:fs-dev kind x0 is3 OX OY)
    (setq brkL (cons (list x0 (+ x0 *gip:FS-BL*)) brkL))
    (if (member kind '("qfd" "qd")) (setq brkN (cons (list x0 (+ x0 *gip:FS-BL*)) brkN)))
    (cond ((= kind "qf") (gip:fs-text "lblQF" x0 OX OY (strcat "QF " (itoa (gip:g c "postIn")) "А")))
          (T (gip:fs-text "lbl2a" x0 OX OY (if (= kind "qd") "QD" "QFD"))
             (gip:fs-text "lbl2b" x0 OX OY (strcat (itoa (if (= kind "qd") (gip:g c "rcdIn") (gip:g c "postIn"))) "А/" (itoa (gip:g c "idn")) "мА")))))
  (setq pre (gip:g c "pre") x0 (+ 6500.308914521 dq))
  (gip:fs-dev pre x0 is3 OX OY)
  (setq brkL (cons (list x0 (+ x0 *gip:FS-BL*)) brkL))
  (gip:fs-text "lbl1" x0 OX OY (strcat (if (= pre "qf") "QF " "QS ") (itoa (gip:g c "preIn")) "А"))
  ;; провода L и N (PE — из прототипа)
  (gip:fs-wire *gip:FS-LY* *gip:FS-X* 7728.927631497 brkL OX OY)
  (gip:fs-wire *gip:FS-NY* *gip:FS-X* 7593.090416282 brkN OX OY))

;; лист si однолинейной схемы с началом координат OX OY
(defun gip:ol-sheet (S BRD sc si npages OX OY / is3 b isfirst islast kup by km inD fire rns bname nC lastX XR XT XTr dxr nChain
                      sub chain y0 xi yb kk2 tx ty w1 hh px2 w2 HD hh2 phs Kc LNS spw sqv cosl ph PRAS Ip rows lb lxx rcdBus
                      ci x AX d l pl members xe yL yN srcY vr nY isD proto tk cs nmt AXk title titleF ks k1 k2 cn kk yy base px py rr q ii xx on inType)
  (setq is3 (= (gip:g S "phases") 3) b *gip:b* isfirst (= si 0) islast (= si (1- npages)) kup (gip:g S "kup"))
  (setq bname (gip:gn S "board" "ЩР"))
  (setq km nil inD nil fire nil rns nil)
  (foreach d (gip:g BRD "all")
    (cond ((= (gip:g d "id") "km") (setq km d)) ((= (gip:g d "id") "in") (setq inD d)) ((= (gip:g d "id") "fire") (setq fire d))
          ((= (gip:g d "kind") "rn") (setq rns (append rns (list d))))))
  (gip:place "frame" OX OY nil)
  (gip:place "head" OX OY nil)
  (setq title (strcat "Принципиальная однолинейная схема щита " bname (if (> npages 1) (strcat " ч." (itoa (1+ si))) "")))
  (gip:place (if is3 "shr3" "shr1") OX OY '(lambda (its) (mapcar '(lambda (it) (if (and (= (car it) "E") (= (gip:it-get it 1) "ЩР")) (gip:it-set it 1 bname) it)) its)))
  (gip:place (if is3 "lbl3" "lbl1") OX OY nil)
  (setq nC (+ (length sc) (if (and islast kup) 1 0)))
  (setq lastX (+ *gip:C0* (* (max (1- nC) 0) *gip:PITCH*)))
  (setq XR (max (+ lastX 681.0) (+ *gip:C0* 681.0 *gip:PITCH*)))
  (setq XT (- (+ *gip:C0* (* (max nC 1) *gip:PITCH*)) 392.7))
  (setq dxr (- XR 18448.3))
  (gip:place "busL" OX OY '(lambda (its / it x1) (setq it (car its) x1 (cadr (assoc 10 (cdr it))))
                             (list (gip:it-poly it (list x1 (+ OY *gip:YB_L*) (+ OX XR) (+ OY *gip:YB_L*))))))
  (gip:place "busN" OX OY '(lambda (its / it p) (setq it (car its) p (assoc 11 (cdr it)))
                             (list (cons "E" (subst (list 11 (+ OX XR) (caddr p) (cadddr p)) p (cdr it))))))
  (gip:place "busPE" OX OY '(lambda (its / it p) (setq it (car its) p (assoc 11 (cdr it)))
                              (list (cons "E" (subst (list 11 (+ OX XR) (caddr p) (cadddr p)) p (cdr it))))))
  (gip:place "slashL" OX OY (if is3 nil '(lambda (its) (list (car its)))))
  (gip:place "slashR" (+ OX dxr) OY (if is3 nil '(lambda (its) (list (car its)))))
  (gip:place (if is3 "lblR3" "lblR1") (+ OX dxr) OY nil)
  (setq nChain (+ 1 (if rns 1 0) (if fire 1 0)))
  (setq yy (+ OY (if (and isfirst (> nChain 2)) 1010.0 449.9)))
  (gip:PL (list (+ OX 2385.5) yy (+ OX XR 323.0) yy (+ OX XR 323.0) (- OY 3176.0) (+ OX 2385.5) (- OY 3176.0) (+ OX 2385.5) yy) "rectDev")
  (gip:PL (list (+ OX 2385.5) (+ OY (nth 0 *gip:YT*)) (+ OX XT) (+ OY (nth 0 *gip:YT*)) (+ OX XT) (+ OY (nth 4 *gip:YT*)) (+ OX 2385.5) (+ OY (nth 4 *gip:YT*))) "rectTab")
  (setq XTr (if (and islast kup) (- (+ *gip:C0* (* (length sc) *gip:PITCH*)) 392.7) XT))
  (foreach r '(1 2 3) (gip:PL (list (+ OX 3238.3) (+ OY (nth r *gip:YT*)) (+ OX XTr) (+ OY (nth r *gip:YT*))) nil))
  ;; ---- ввод
  (if isfirst
    (progn
      (if (gip:g S "floorShield") (gip:floor-shield S OX OY is3))
      (setq inType (if (= (gip:g inD "inType") "qs") "qs" "qf"))
      (setq chain (list (list (cons "p" (cond ((= inType "qs") (if is3 "rel3" "rel1")) (is3 "in3") (T "dev_a1"))) (cons "rel" is3) (cons "d" inD)
                              (cons "o" (if (= inType "qs")
                                (list '("ser" . "Рубильник") '("maker" . "—") (cons "vis" (if is3 "Рубильник трехполюсный" "Рубильник однополюсный")))
                                (list (cons "ser" (if is3 (gip:brand-ser b (if (= (gip:g S "inPoles") 4) "a4" "a3") nil) (gip:brand-ser b "a2" nil)))
                                      (cons "vis" (gip:av-vis (if is3 (if (= (gip:g S "inPoles") 4) 4 3) 2)))))))))
      (if rns (setq chain (append chain (list (list (cons "p" (if is3 "rel3" "rel1")) (cons "rel" T) (cons "d" '(("In" . 63)))
                                                    (cons "o" (list (cons "ser" (if is3 "VIP-63 x3" "VIP-63")) '("maker" . "Welrok")
                                                                    (cons "ref" (gip:join (mapcar '(lambda (r) (gip:g r "ref")) rns) ", ")))))))))
      (if fire (setq chain (append chain (list (list (cons "p" (if is3 "dev_d3" "dev_d1")) (cons "rel" nil) (cons "d" fire)
                                                     (cons "o" (list '("ma" . "100") (cons "ser" (gip:rcd-ser (gip:g b (if is3 "fire4" "fire2")))) '("type" . "АC") (cons "vis" (gip:rcd-vis is3)))))))))
      (setq y0 (if (> (length chain) 2) 787.0 169.0) xi 3973.06 kk 0)
      (foreach cn chain
        (setq yy (- y0 (* kk 618.0)))
        (if (gip:g cn "rel")
          (setq px OX py (+ OY (if (= (gip:g cn "p") "in3") (- yy 168.7) (+ yy 449.4))))
          (setq px (+ OX xi) py (+ OY yy)))
        (setq rr cn)
        (gip:place (gip:g cn "p") px py '(lambda (its) (gip:dev-atts its (gip:g rr "d") (gip:g rr "o"))))
        (setq kk (1+ kk)))
      (setq yb (- y0 (* (length chain) 618.0)))
      (if (gip:g S "floorShield")
        (progn
          (gip:place "ln_Ltop" 0.0 0.0 '(lambda (its) (list (gip:it-line (car its) (+ OX xi) (+ OY y0) (+ OX xi) (+ OY 939.0)))))
          (gip:PL (list (+ OX 4137.8) (+ OY y0) (+ OX 4137.8) (+ OY 939.0)) "ln_Ntop")))
      (gip:PL (list (+ OX 4137.8) (+ OY *gip:YB_N*) (+ OX 4137.8) (+ OY yb)) "ln_Nbot")
      (gip:PL (list (+ OX xi) (+ OY yb) (+ OX xi) (+ OY *gip:YB_L*)) "ln_Lbot")
      (gip:PL (list (+ OX 4302.6) (+ OY *gip:YB_PE*) (+ OX 4302.6) (+ OY (if (gip:g S "floorShield") 939.0 yb))) "ln_PE")
      (gip:dot (+ OX xi) (+ OY *gip:YB_L*) T) (gip:dot (+ OX 4137.8) (+ OY *gip:YB_N*) T) (gip:dot (+ OX 4302.6) (+ OY *gip:YB_PE*) T)
      (if km
        (progn
          (setq ks (gip:km-split (gip:gn km "model" "")) k1 (car ks) k2 (cadr ks))
          (gip:place (if is3 "km3" "km1") OX OY '(lambda (its) (mapcar '(lambda (it / t1) (setq t1 (if (= (car it) "E") (gip:it-get it 1)))
                                                                               (cond ((= t1 "ESB") (gip:it-set it 1 k1)) ((= t1 "63-40N") (gip:it-set it 1 k2)) (T it))) its)))
          (gip:place "kmname" OX OY nil)))
      ;; ---- показатели
      (setq Kc (gip:gn S "kc" 0.4) LNS (gip:g BRD "lines"))
      (setq spw (gip:sum (mapcar '(lambda (l) (gip:g l "p")) LNS)))
      (setq sqv (gip:sum (mapcar '(lambda (l) (/ (gip:g l "p") (gip:cos l))) LNS)))
      (setq cosl (if (> sqv 0) (/ (gip:round (* (/ spw sqv) 100)) 100.0) 0.9))
      (setq ph (list (cons "A" 0.0) (cons "B" 0.0) (cons "C" 0.0)))
      (foreach l LNS
        (cond ((not is3) (setq ph (gip:s ph "A" (+ (gip:g ph "A") (gip:g l "p")))))
              ((= (gip:g l "phase") "L123") (foreach q '("A" "B" "C") (setq ph (gip:s ph q (+ (gip:g ph q) (/ (gip:g l "p") 3.0))))))
              (T (setq q (cdr (assoc (gip:g l "phase") '(("L1" . "A") ("L2" . "B") ("L3" . "C")))))
                 (setq ph (gip:s ph q (+ (gip:g ph q) (gip:g l "p")))))))
      (setq PRAS (* spw Kc) Ip (if is3 (/ PRAS (* (sqrt 3.0) 0.4 cosl)) (/ PRAS (* 0.23 cosl))))
      ;; таблица по фазам: при одной фазе — только столбец A без заголовка
      (setq phs (if is3 '("A" "B" "C") '("A")))
      (setq tx (+ OX 8400.0) ty (+ OY 3550.0) kk2 *gip:KU* w1 (* (if is3 85 41) kk2) hh (* 34 kk2) px2 (+ tx w1) w2 (* 118 kk2) HD 500.0 hh2 (+ HD (* 30 kk2)))
      (gip:PL (list tx ty (+ px2 w2) ty (+ px2 w2) (- ty hh2) tx (- ty hh2) tx ty) nil)
      (gip:PL (list tx (- ty HD) (+ tx w1) (- ty HD)) nil)
      (gip:PL (list px2 ty px2 (- ty hh2)) nil)
      (foreach mm (if is3 '(19 41 63) '(19)) (gip:PL (list (+ tx (* mm kk2)) ty (+ tx (* mm kk2)) (- ty hh2)) nil))
      (foreach mm '(10 20) (gip:PL (list tx (- ty HD (* mm kk2)) (+ tx w1) (- ty HD (* mm kk2))) nil))
      (setq ii 0)
      (if is3 (foreach t1 '("Фаза A" "Фаза B" "Фаза C") (gip:ol-cell (+ tx (* (+ 30 (* ii 22)) kk2)) (- ty (/ HD 2)) t1 nil) (setq ii (1+ ii))))
      (foreach r (list '("Pуст., кВт" . 5) '("Pр., кВт" . 15) '("Iрасч., А" . 25)) (gip:ol-cell (+ tx (* 9.5 kk2)) (- ty HD (* (cdr r) kk2)) (car r) nil))
      (setq ii 0)
      (foreach pp phs
        (setq xx (+ tx (* (+ 30 (* ii 22)) kk2)) on (member pp phs))
        (gip:ol-cell xx (- ty HD (* 5 kk2)) (if on (gip:f1 (gip:g ph pp)) "—") nil)
        (gip:ol-cell xx (- ty HD (* 15 kk2)) (if on (gip:f1 (* (gip:g ph pp) Kc)) "—") nil)
        (gip:ol-cell xx (- ty HD (* 25 kk2)) (if on (gip:f1 (/ (* (gip:g ph pp) Kc) (* 0.23 cosl))) "—") nil)
        (setq ii (1+ ii)))
      (gip:mt "cell_qty" (+ px2 (/ w2 2)) (- ty (/ HD 2)) "Основные показатели проекта" (list (cons "w" 5889.026) (cons "att" 5)))
      (setq rows (list (cons "Напряжение сети, В" (if is3 "400/230" "230")) (cons "Установленная мощность, кВт" (gip:f1 spw))
                       (cons "Расчетная мощность, кВт" (gip:f1 PRAS)) (cons "Расчетный ток, А" (gip:f1 Ip))
                       (cons "Коэффициент спроса" (gip:fmtz Kc 2)) (cons "Средневзвешенный cos φ" (gip:fmtz cosl 2))))
      (setq ii 0)
      (foreach rw rows
        (setq yy (- ty HD (* ii 5 kk2)))
        (gip:PL (list px2 yy (+ px2 w2) yy) nil)
        (gip:ol-cell (+ px2 (* 1.5 kk2)) (- yy (* 2.5 kk2)) (car rw) T)
        (gip:ol-cell (+ px2 (* 107.5 kk2)) (- yy (* 2.5 kk2)) (cdr rw) nil)
        (setq ii (1+ ii)))))
  ;; ---- шина освещения
  (setq lb (vl-remove-if-not '(lambda (c) (and (= (gip:g c "t") "line") (= (gip:g (gip:g c "d") "feed") "km"))) sc))
  (if (and isfirst km lb)
    (progn (setq lxx (+ *gip:C0* (* (gip:index (last lb) sc) *gip:PITCH*)))
           (gip:PL (list (+ OX 3053.5) (+ OY *gip:YB_LB*) (+ OX lxx) (+ OY *gip:YB_LB*)) "lightbus")))
  ;; ---- колонки
  (setq rcdBus nil ci 0)
  (foreach c sc
    (setq x (+ *gip:C0* (* ci *gip:PITCH*)) AX (+ OX x) d (gip:g c "d") l (gip:g d "line"))
    (gip:PL (list (- AX 392.7) (+ OY (nth 0 *gip:YT*)) (- AX 392.7) (+ OY (nth 4 *gip:YT*))) nil)
    (if is3
      (progn
        (setq pl (if (= (gip:g c "t") "rcd")
                   (if (= (gip:g d "w") 4) "ABC" (gip:gn (list '("L1" . "A") '("L2" . "B") '("L3" . "C")) (gip:g d "phase") ""))
                   (if (or (= (gip:g d "phase") "L123") (member (gip:g d "kind") '("a3" "dif4"))) "ABC"
                     (gip:gn (list '("L1" . "A") '("L2" . "B") '("L3" . "C")) (gip:g d "phase") ""))))
        (gip:mt "m_phase" (- AX (if (> (strlen pl) 1) 316.0 135.5)) (- OY 1868.0) pl nil)))
    (if (= (gip:g c "t") "rcd")
      (progn
        (setq members (vl-remove-if-not '(lambda (m) (= (gip:g (gip:g m "d") "feed") (gip:g d "id"))) sc))
        (setq xe (+ OX *gip:C0* (* (gip:index (last members) sc) *gip:PITCH*)) yL -1712.0 yN -1782.0)
        (gip:dot AX (+ OY *gip:YB_L*) nil) (gip:dot (+ AX 165) (+ OY *gip:YB_N*) nil)
        (gip:W AX (+ OY *gip:YB_L*) AX (+ OY *gip:YDEV*)) (gip:W (+ AX 165) (+ OY *gip:YB_N*) (+ AX 165) (+ OY *gip:YDEV*))
        (setq rr d)
        (gip:place "dev_d1" AX (+ OY *gip:YDEV*) '(lambda (its) (gip:dev-atts its rr (list (cons "ma" (itoa (gip:gn rr "idn" 30))) (cons "ser" (gip:rcd-ser (gip:g *gip:b* (if (= (gip:g rr "w") 4) "rcd4" "rcd2")))) (cons "type" (if (= (gip:g rr "type") "AC") "АС" "А")) (cons "vis" (gip:rcd-vis (= (gip:g rr "w") 4)))))))
        (gip:W AX (+ OY *gip:YDB*) AX (- OY 2700.0)) (gip:W AX (- OY 2700.0) (+ AX 250) (- OY 2700.0)) (gip:W (+ AX 250) (- OY 2700.0) (+ AX 250) (+ OY yL))
        (gip:W (+ AX 165) (+ OY *gip:YDB*) (+ AX 165) (- OY 2655.0)) (gip:W (+ AX 165) (- OY 2655.0) (+ AX 330) (- OY 2655.0)) (gip:W (+ AX 330) (- OY 2655.0) (+ AX 330) (+ OY yN))
        (gip:PL (list (+ AX 250) (+ OY yL) xe (+ OY yL)) "lightbus")
        (gip:W (+ AX 330) (+ OY yN) (+ xe 165) (+ OY yN))
        (setq rcdBus (cons (cons (gip:g d "id") (list yL yN)) rcdBus))
        (gip:mt "cell_qty" AX (- OY 4845.0) "—" (list (cons "w" 700.0))))
      (progn
        (setq srcY *gip:YB_L* vr (cdr (assoc (gip:g d "feed") rcdBus)))
        (if (and (= (gip:g d "feed") "km") km) (setq srcY *gip:YB_LB*))
        (if vr (setq srcY (car vr)))
        (setq nY (if vr (cadr vr) *gip:YB_N*) isD (member (gip:g d "kind") '("dif" "dif4")))
        (setq proto (cond ((= (gip:g d "kind") "dif4") "dev_d3") ((= (gip:g d "kind") "dif") "dev_d1") ((= (gip:g d "kind") "a3") "dev_a3") (T "dev_a1")))
        (gip:dot AX (+ OY srcY) nil) (gip:dot (+ AX 165) (+ OY nY) nil) (gip:dot (+ AX 266) (+ OY *gip:YB_PE*) nil)
        (gip:W AX (+ OY srcY) AX (+ OY *gip:YDEV*)) (gip:W (+ AX 165) (+ OY nY) (+ AX 165) (+ OY *gip:YDEV*))
        (setq tk (gip:g d "kind") rr d)
        (gip:place proto AX (+ OY *gip:YDEV*)
          '(lambda (its) (gip:dev-atts its rr (list (cons "ser" (gip:brand-ser *gip:b* tk (gip:g rr "In")))
                                                    (cons "ma" (if isD (itoa (gip:gn rr "idn" 30)))) (cons "type" (if isD "А"))))))
        (gip:W (+ AX 165) (+ OY *gip:YDB*) (+ AX 165) (+ OY *gip:YKN*)) (gip:W (+ AX 165) (+ OY *gip:YKN*) AX (+ OY *gip:YMG*))
        (gip:W (+ AX 266) (+ OY *gip:YB_PE*) (+ AX 266) (+ OY *gip:YKN*)) (gip:W (+ AX 266) (+ OY *gip:YKN*) AX (+ OY *gip:YMG*))
        (if (not (gip:g l "reserve"))
          (progn
            (setq cs (gip:consumer l))
            (gip:W AX (+ OY *gip:YDB*) AX (+ OY (caddr cs)))
            (setq rr (list c l))
            (gip:place (car cs) AX (+ OY (cadr cs))
              '(lambda (its) (mapcar '(lambda (it) (gip:it-atts it (list (cons "ПОЗИЦИЯ" (gip:g (car rr) "no")) (cons "ИМЯ" (gip:g (cadr rr) "name")) (cons "ОПИСАНИЕ" (gip:g (cadr rr) "name"))))) its)))
            (gip:mt "m_cable" (- AX 157.0) (- OY 4195.5) (strcat (gip:mark-short (gip:gn S "mark" "ВВГнг(А)-LS")) " " (gip:repl (gip:g l "cable") "×" "x")) nil)
            ;; длина кабеля на схеме — по галочке «Длины кабелей на схеме»
            (gip:mt "m_cond" (+ AX 64.0) (- OY 4195.5) (strcat (gip:conduit (gip:g l "cable")) (if (gip:g S "olLen") (strcat " L=" (itoa (gip:g l "len")) " м") "")) nil)))
        (gip:mt "cell_qty" AX (- OY 4845.0) (gip:g c "no") (list (cons "w" 700.0)))
        (gip:mt "cell_qty" AX (- OY 5293.0) (gip:f1 (gip:g l "p")) (list (cons "w" 700.0)))
        (gip:mt "cell_qty" AX (- OY 5591.0) (gip:f1 (gip:inom l)) (list (cons "w" 700.0)))
        (setq nmt (gip:take (gip:wrap (if (gip:starts (gip:g l "name") "Освещение: ") (strcat "Освещение " (substr (gip:g l "name") 12)) (gip:g l "name")) 16) 3))
        (gip:mt "m_name" (+ (- AX 300.0) (if (= (length nmt) 1) 120.0 0.0)) (- OY 7022.0) (gip:join nmt "\n") (list (cons "w" 1282.0)))))
    (setq ci (1+ ci)))
  ;; ---- КУП
  (if (and islast kup)
    (progn
      (setq AXk (+ OX *gip:C0* (* (length sc) *gip:PITCH*)))
      (gip:PL (list (- AXk 392.7) (+ OY (nth 0 *gip:YT*)) (- AXk 392.7) (+ OY (nth 4 *gip:YT*))) nil)
      (gip:dot AXk (+ OY *gip:YB_PE*) nil) (gip:W AXk (+ OY *gip:YB_PE*) AXk (- OY 4360.5))
      (gip:place "kup" AXk OY
        '(lambda (its) (mapcar '(lambda (it)
                                  (if (and (= (car it) "E") (= (gip:it-get it 0) "MTEXT") (gip:has (gip:gn (cdr it) 1 "") "Коробки"))
                                    (progn
                                      (setq it (gip:it-text it "Коробки дополнительной\nсистемы уравнивания\nпотенциалов"))
                                      (setq it (gip:it-set it 41 2493.87862559041))
                                      (cons "E" (subst (list 10 (- AXk 300.0) (- OY 7022.0) 0.0) (assoc 10 (cdr it)) (cdr it))))
                                    it)) its)))))
  ;; ---- штамп
  (gip:stamp-st OX OY title (itoa (+ 2 si)) "")
  title)

(defun gip:ol-cell (x y txt left)
  (gip:mt (if left "cell_name" "cell_qty") x y txt (list (cons "w" (if left 0.0 1000.0)) (cons "att" (if left 4 5)))))

;; надписи основного штампа листа схемы: название, стадия, лист, листов
(defun gip:stamp-st (OX OY title no tot)
  (gip:mt "st_title" OX OY title nil)
  (gip:mt "st_stage" OX OY (gip:gn *gip:S* "stage" "Р") nil)
  (gip:mt "st_no" OX OY no nil)
  (if (and tot (/= tot "")) (gip:mt "st_no" (+ OX 850.0) OY tot (list (cons "w" 900.0)))))
