;;; ============================================================================
;;; Модель щита: групповые линии, аппараты, раскладка по рейкам, обозначения
;;; (перенос логики конструктора gipproekt.ru один в один)
;;; ============================================================================

(defun gip:line (id name cat prot poles In p / l)
  (list (cons "id" id) (cons "name" name) (cons "cat" cat) (cons "prot" prot) (cons "poles" poles) (cons "In" In) (cons "p" p)))

(defun gip:build-lines (s / LNS is3 app i n f a lst edit o light1 split3 rest k)
  (setq LNS nil is3 (= (gip:g s "phases") 3) app (gip:g s "app") edit (gip:g s "edit"))
  (setq i 0)
  (foreach n (gip:g s "light")
    (setq LNS (cons (gip:s (gip:line (strcat "light" (itoa i) ":" n) (strcat "Освещение: " n) "light" "a" 1 10 0.3) "km" T) LNS) i (1+ i)))
  (if (gip:g app "hob")
    (setq LNS (cons (if is3 (gip:line "hob" "Варочная панель" "hob" "a" 3 16 7.5) (gip:line "hob" "Варочная панель" "hob" "a" 1 32 7.0)) LNS)))
  (if (gip:g app "oven") (setq LNS (cons (gip:line "oven" "Духовой шкаф" "app" "d" 1 16 3.5) LNS)))
  (if (gip:g app "fridge") (setq LNS (cons (gip:line "fridge" "Холодильник" "app" "d" 1 16 0.5) LNS)))
  (if (gip:g app "dw") (setq LNS (cons (gip:line "dw" "ПММ и измельчитель" "app" "d" 1 16 2.2) LNS)))
  (if (gip:g app "wash") (setq LNS (cons (gip:line "wash" "Стиральная машина" "app" "d" 1 16 2.3) LNS)))
  (if (gip:g app "dry") (setq LNS (cons (gip:line "dry" "Сушильная машина" "app" "d" 1 16 2.5) LNS)))
  (setq i 0)
  (foreach n (gip:g s "sockets")
    (setq LNS (cons (gip:line (strcat "sock" (itoa i) ":" n) n "sock" "d" 1 16 1.5) LNS) i (1+ i)))
  (setq f 1)
  (while (<= f (gip:gn s "floor" 0))
    (setq LNS (cons (gip:line (strcat "floor" (itoa f)) (strcat "Тёплый пол" (if (> (gip:g s "floor") 1) (strcat " " (itoa f)) "")) "floor" "d" 1 16 1.2) LNS) f (1+ f)))
  (cond ((= (gip:g s "heater") "boiler") (setq LNS (cons (gip:line "heater" "Водонагреватель накопительный" "heat" "d" 1 16 2.0) LNS)))
        ((= (gip:g s "heater") "flow")
         (setq LNS (cons (if is3 (gip:line "heater" "Водонагреватель проточный" "heat" "d3" 3 16 9.0) (gip:line "heater" "Водонагреватель проточный" "heat" "d" 1 32 6.0)) LNS))))
  (if (gip:g app "leak") (setq LNS (cons (gip:line "leak" "Защита от протечек и слаботочный щит" "leak" "d" 1 16 0.2) LNS)))
  (setq a 1)
  (while (<= a (gip:gn s "ac" 0))
    (setq LNS (cons (gip:line (strcat "ac" (itoa a)) (strcat "Кондиционер" (if (> (gip:g s "ac") 1) (strcat " " (itoa a)) "")) "ac" "a" 1 16 1.2) LNS) a (1+ a)))
  (foreach c (gip:g s "custom")
    (setq LNS (cons (gip:s (gip:line (gip:g c "id") (gip:g c "name") "custom" (gip:g c "prot") (gip:g c "poles") (gip:g c "In") (gip:g c "p")) "custom" T) LNS)))
  (setq LNS (reverse LNS))
  ;; правки пользователя
  (setq LNS (vl-remove-if '(lambda (l) (member (gip:g l "id") (gip:g s "removed"))) LNS))
  (setq LNS (mapcar '(lambda (l / o kv)
                     (setq o (gip:g edit (gip:g l "id")))
                     (foreach kv o (setq l (gip:s l (car kv) (cdr kv))))
                     (setq l (gip:s l "cable" (if (gip:g o "cable") (gip:g o "cable") (gip:cable-for (gip:g l "In") (gip:g l "poles") (= (gip:g l "cat") "light")))))
                     (if (and (= (gip:g l "cat") "hob") (= (gip:g l "poles") 3) (not (gip:g o "cable"))) (setq l (gip:s l "cable" "5×4")))
                     l) LNS))
  ;; фазы
  (if is3
    (progn
      (setq LNS (mapcar '(lambda (l) (if (= (gip:g l "poles") 3) (gip:s l "phase" "L123") l)) LNS))
      ;; освещение: по трём фазам по порядку
      (setq light1 (vl-remove-if-not '(lambda (l) (and (= (gip:g l "cat") "light") (= (gip:g l "poles") 1))) LNS))
      (setq n (length light1) k 0)
      (setq LNS (mapcar '(lambda (l / idx)
                         (if (setq idx (gip:index l light1))
                           (gip:s l "phase" (nth (min 2 (fix (/ (* idx 3.0) (max n 1)))) '("L1" "L2" "L3")))
                           l)) LNS))
      ;; остальные однофазные — тремя сплошными участками с ровной мощностью
      (setq rest (vl-remove-if-not '(lambda (l) (and (= (gip:g l "poles") 1) (/= (gip:g l "cat") "light"))) LNS))
      (setq LNS (gip:split3 LNS rest))
      (setq LNS (mapcar '(lambda (l / o) (setq o (gip:g edit (gip:g l "id")))
                         (if (and (gip:g o "phase") (= (gip:g l "poles") 1)) (gip:s l "phase" (gip:g o "phase")) l)) LNS)))
    (setq LNS (mapcar '(lambda (l) (gip:s l "phase" (if (= (gip:g l "poles") 3) "L123" "L"))) LNS)))
  LNS)

;; деление последовательности на три участка L1/L2/L3 (как split3 в конструкторе)
(defun gip:split3 (LNS arr / n pre i j a1 a2 a3 m cnt best k ids res)
  (setq n (length arr))
  (if (= n 0)
    LNS
    (progn
      (setq pre (list 0.0))
      (foreach l arr (setq pre (append pre (list (+ (last pre) (gip:g l "p"))))))
      (setq best nil i 0)
      (while (<= i n)
        (setq j i)
        (while (<= j n)
          (setq a1 (nth i pre) a2 (- (nth j pre) (nth i pre)) a3 (- (nth n pre) (nth j pre)))
          (setq m (max a1 a2 a3))
          (setq cnt (- (max i (- j i) (- n j)) (min i (- j i) (- n j))))
          (if (or (null best) (< m (- (car best) 1e-9)) (and (< (abs (- m (car best))) 1e-9) (< cnt (cadr best))))
            (setq best (list m cnt i j)))
          (setq j (1+ j)))
        (setq i (1+ i)))
      (setq ids (mapcar '(lambda (l) (gip:g l "id")) arr))
      (mapcar '(lambda (l / k)
                 (if (setq k (gip:index (gip:g l "id") ids))
                   (gip:s l "phase" (cond ((< k (nth 2 best)) "L1") ((< k (nth 3 best)) "L2") (T "L3")))
                   l)) LNS))))

(defun gip:std-up (v lst / r)
  (setq r nil)
  (foreach x lst (if (and (null r) (>= x v)) (setq r x)))
  (if r r (last lst)))

(defun gip:dev (pairs) pairs)

;; общие аппараты щита: ввод, реле, УЗО 100 мА, кросс-модуль, КМ (используют переменные вызывающей функции: b is3 useKm)
(defun gip:fixed-devs (s lines / D inPoles inP fi hasLight bn kt inType)
  (setq D nil)
  (setq inPoles (if is3 (if (= (gip:g s "inPoles") 4) 4 3) 2))
  (setq inP (if is3 (if (= inPoles 4) '("L1" "L2" "L3" "N") '("L1" "L2" "L3")) '("L" "N")))
  (setq bn (gip:g b "name") inType (if (= (gip:g s "inType") "qs") "qs" "qf"))
  (setq D (cons (list '("id" . "in") '("kind" . "in") (cons "inType" inType) (cons "w" inPoles) (cons "poles" inP) (cons "bot" inP) (cons "In" (gip:g s "inA"))
                      (cons "model" (if (= inType "qs") (strcat "Рубильник " (itoa inPoles) "P, " (itoa (gip:g s "inA")) " А") (gip:fmt-model (if is3 (if (= inPoles 4) (gip:g b "a4") (gip:g b "a3")) (gip:g b "a2")) (gip:g s "inA"))))
                      (cons "name" (if (= inType "qs") "Вводной рубильник" "Вводной автомат")) (cons "brand" (if (= inType "qs") "—" bn)) '("feed" . "ext")) D))
  (if (gip:g s "relay")
    (if is3
      (foreach p '("L1" "L2" "L3")
        (setq D (cons (list (cons "id" (strcat "rn" (substr p 2 1))) '("kind" . "rn") '("w" . 2) '("poles") '("bot" "L" "N" "Lo") (cons "phase" p) '("In" . 63)
                            '("model" . "VIP-63 63А") (cons "name" (strcat "Реле напряжения " p)) '("brand" . "Welrok") '("feed" . "in")) D)))
      (setq D (cons (list '("id" . "rn1") '("kind" . "rn") '("w" . 2) '("poles") '("bot" "L" "N" "Lo") '("phase" . "L") '("In" . 63)
                          '("model" . "VIP-63 63А") '("name" . "Реле напряжения") '("brand" . "Welrok") '("feed" . "in")) D))))
  (if (gip:g s "fire")
    (progn
      (setq fi (gip:std-up (max (gip:g s "inA") 40) '(40 63 80 100)))
      (setq D (cons (list '("id" . "fire") '("kind" . "fire") (cons "w" (if is3 4 2))
                          (cons "poles" (if is3 '("L1" "L2" "L3" "N") '("L" "N"))) (cons "bot" (if is3 '("L1" "L2" "L3" "N") '("L" "N")))
                          (cons "In" fi) (cons "model" (gip:fmt-model (if is3 (gip:g b "fire4") (gip:g b "fire2")) fi))
                          '("name" . "УЗО противопожарное 100 мА") (cons "brand" bn) '("feed" . "up")) D))))
  (if (gip:g s "xb")
    (setq D (cons (list '("id" . "xb") '("kind" . "xb") (cons "w" (if is3 5 3))
                        (cons "poles" (if is3 '("L1" "L2" "L3" "N") '("L" "N"))) (cons "bot" (if is3 '("L1" "L2" "L3" "N") '("L" "N")))
                        (cons "model" (if is3 "4П, 125 А" "2П, 125 А")) '("name" . "Кросс-модуль") '("brand" . "—") '("feed" . "up")) D)))
  (if useKm
    (progn
      (setq D (cons (list '("id" . "c2") '("kind" . "a1") '("w" . 1) '("poles" "L") '("bot" "L") (cons "phase" (if is3 "L1" "L")) '("In" . 2)
                          (cons "model" (gip:fmt-model (gip:g b "a1") 2)) '("name" . "Защита катушки КМ") (cons "brand" bn) '("feed" . "src")) D))
      (setq kt (gip:km-of s))
      (setq D (cons (list '("id" . "km") '("kind" . "km") (cons "w" (nth 3 kt)) (cons "kmType" (car kt)) (cons "kmI" (cadr kt)) (cons "kmC" (caddr kt))
                          (cons "poles" (if is3 '("A1" "L1" "L2" "L3") '("A1" "L"))) (cons "bot" (if is3 '("A2" "L1" "L2" "L3") '("A2" "L")))
                          (cons "model" (gip:km-model s kt)) '("name" . "Контактор «мастер-выключатель»") (cons "brand" bn) '("feed" . "src")) D))))
  (reverse D))

;; аппараты щита (режим шаблона)
(defun gip:build-devices (s lines / b is3 D hasLight useKm rcdN ri run)
  (setq b (gip:brand (gip:g s "brand")) is3 (= (gip:g s "phases") 3))
  (setq hasLight (vl-some '(lambda (l) (gip:g l "km")) lines))
  (setq useKm (and (gip:g s "km") hasLight))
  (setq D (reverse (gip:fixed-devs s lines)))
  (setq rcdN 0 ri (max 40 (gip:std-up (gip:g s "inA") '(25 40 63 80))) run nil)
  (foreach l lines
    (cond
      ((gip:g l "km")
       (gip:flush-run) (setq D (cons (gip:line-dev l (if useKm "km" "src")) D)))
      ((and (= (gip:g s "prot") "rcd") (= (gip:g l "prot") "d") (= (gip:g l "poles") 1))
       (if (and run (/= (gip:g (car run) "phase") (gip:g l "phase"))) (gip:flush-run))
       (setq run (append run (list l))))
      (T (gip:flush-run) (setq D (cons (gip:line-dev l "src") D)))))
  (gip:flush-run)
  (reverse D))

;; вспомогательные функции build-devices (используют переменные вызывающей функции: D run rcdN ri b s)
(defun gip:line-dev (l feed / d)
  (setq d (list (cons "id" (strcat "L:" (gip:g l "id"))) (cons "line" l) (cons "name" (gip:g l "name")) (cons "In" (gip:g l "In"))
                (cons "phase" (gip:g l "phase")) (cons "feed" feed) (cons "brand" (gip:g b "name"))))
  (cond
    ((= (gip:g l "poles") 3)
     (if (= (gip:g l "prot") "d3")
       (setq d (append d (list '("kind" . "dif4") '("w" . 4) '("poles" "L1" "L2" "L3" "N") '("bot" "L1" "L2" "L3" "N")
                               (cons "model" (gip:fmt-model (gip:g b "dif4") (gip:g l "In"))))))
       (setq d (append d (list '("kind" . "a3") '("w" . 3) '("poles" "L1" "L2" "L3") '("bot" "L1" "L2" "L3")
                               (cons "model" (gip:fmt-model (gip:g b "a3") (gip:g l "In"))))))))
    ((and (= (gip:g l "prot") "d") (= (gip:g s "prot") "dif"))
     (setq d (append d (list '("kind" . "dif") '("w" . 2) '("poles" "L" "N") '("bot" "L" "N") (cons "model" (gip:fmt-model (gip:g b "dif") (gip:g l "In")))))))
    (T (setq d (append d (list '("kind" . "a1") '("w" . 1) '("poles" "L") '("bot" "L") (cons "model" (gip:fmt-model (gip:g b "a1") (gip:g l "In"))))))))
  d)

(defun gip:rcd-group (ls / rid ph)
  (setq rcdN (1+ rcdN) rid (strcat "rcd" (itoa rcdN) ":" (gip:g (car ls) "id")) ph (gip:g (car ls) "phase"))
  (setq D (cons (list (cons "id" rid) '("kind" . "rcd") '("w" . 2) '("poles" "L" "N") '("bot" "L" "N") (cons "phase" ph) (cons "In" ri)
                      (cons "model" (gip:fmt-model (gip:g b "rcd2") ri)) (cons "name" (strcat "УЗО группы " (itoa rcdN)))
                      (cons "brand" (gip:g b "name")) '("feed" . "src") (cons "rcdNo" rcdN)) D))
  (foreach l ls (setq D (cons (gip:s (gip:line-dev l rid) "rcdNo" rcdN) D))))

(defun gip:flush-run (/ g sz k)
  (if run
    (progn
      (setq g (gip:ceil (/ (length run) 4.0)) sz (gip:ceil (/ (length run) (float g))) k 0)
      (while (< k (length run))
        (gip:rcd-group (gip:take (gip:drop run k) sz))
        (setq k (+ k sz)))
      (setq run nil))))

;; порядок с учётом перетаскиваний: order — id по порядку, новые — после ближайшего предшественника
(defun gip:apply-order (s DEVS / order out used pos k idx byid j)
  (setq order (gip:g s "order"))
  (if (null order)
    DEVS
    (progn
      (setq out nil used nil)
      (foreach id order
        (foreach d DEVS (if (and (= (gip:g d "id") id) (not (member id used))) (setq out (append out (list d)) used (cons id used)))))
      (setq k 0)
      (foreach d DEVS
        (if (not (member (gip:g d "id") used))
          (progn
            (setq pos 0 idx (1- k))
            (while (>= idx 0)
              (if (and (= pos 0) (setq j (gip:index (nth idx DEVS) out))) (setq pos (1+ j) idx -1))
              (setq idx (1- idx)))
            (setq out (append (gip:take out pos) (list d) (gip:drop out pos)) used (cons (gip:g d "id") used))))
        (setq k (1+ k)))
      out)))

;; раскладка по рейкам
(defun gip:flow-rails (s DEVS / W rails cur used total need i d brk gw j nxt bx)
  (setq W (gip:g s "railW") rails nil cur nil used 0 i 0)
  (foreach d DEVS
    (setq brk (and (or (member (gip:g d "id") (gip:g s "breaks")) (member i (gip:g s "breakAt"))) cur))
    (setq gw (gip:g d "w"))
    (if (and (null (gip:g s "order")) (or (= (gip:g d "kind") "rcd") (= (gip:g d "id") "c2")))
      (progn
        (setq j (1+ i))
        (while (and (< j (length DEVS))
                    (progn (setq nxt (nth j DEVS))
                           (or (= (gip:g nxt "feed") (gip:g d "id"))
                               (and (= (gip:g d "id") "c2") (or (= (gip:g nxt "id") "km") (= (gip:g nxt "feed") "km"))))))
          (setq gw (+ gw (gip:g nxt "w")) j (1+ j)))
        (if (> gw W) (setq gw (gip:g d "w")))))
    (if (or brk (> (+ used gw) W)) (setq rails (append rails (list cur)) cur nil used 0))
    (setq cur (append cur (list d)) used (+ used (gip:g d "w")) i (1+ i)))
  (if cur (setq rails (append rails (list cur))))
  (setq total (gip:sum (mapcar '(lambda (d) (gip:g d "w")) DEVS)))
  (setq need (max (length rails) (gip:ceil (/ (* total 1.2) W))))
  (if (> (gip:gn s "railsMin" 0) 0) (setq need (max need (gip:g s "railsMin"))))
  ;; настоящий корпус ABB: реек на схеме столько же, сколько рядов в корпусе
  (if (setq bx (gip:pick-box W total (max need (length rails)))) (setq need (max need (cadr bx))))
  ;; корпуса больше самого большого у ABB нет (напр. на ряд 18 — 72 мод.): запас рядов сверх каталога не добавляем
  (if (null bx) (setq need (max (length rails) (min need (apply 'max (mapcar 'cadr (cdr (assoc W *gip:boxes*))))))))
  (while (< (length rails) need) (setq rails (append rails (list nil))))
  (list (cons "rails" rails) (cons "used" total) (cons "cap" (* (length rails) W)) (cons "box" bx)))

;; обозначения QF, QFD, QD, KV, KM, XT по порядку на рейках
(defun gip:designate (rails / c p r)
  (setq c '(("QF" . 0) ("QS" . 0) ("QFD" . 0) ("QD" . 0) ("KV" . 0) ("KM" . 0) ("XT" . 0)))
  (mapcar '(lambda (r)
             (mapcar '(lambda (d / k p n)
                        (setq k (gip:g d "kind"))
                        (setq p (cond ((member k '("dif" "dif4")) "QFD") ((member k '("rcd" "fire")) "QD") ((= k "rn") "KV")
                                      ((= k "km") "KM") ((= k "xb") "XT") ((and (= k "in") (= (gip:g d "inType") "qs")) "QS") (T "QF")))
                        (setq n (1+ (gip:g c p)) c (gip:s c p n))
                        (gip:s d "ref" (strcat p (itoa n)))) r)) rails))

(defun gip:cos (l) (if (or (member (gip:g l "cat") '("hob" "heat" "floor")) (= (gip:gn l "key" (gip:g l "id")) "oven")) 1.0 0.9))

;; ориентировочная длина кабеля линии по площади квартиры, м; плюс запас на приборы с планов (*gip:len-extra*: категория . метры на линию)
(setq *gip:len-extra* nil)
(defun gip:cable-len (l area / s cat k c x)
  (setq s (sqrt (max area 15.0)) cat (gip:g l "cat"))
  ;; калибровка по проекту «Сосновая»: свет ~50 м на линию (шлейф по светильникам), розетки ~16 м, техника ~11 м
  (cond ((= cat "light") (setq k 4.0 c 10.0))
        ((= cat "sock") (setq k 1.2 c 4.0))
        ((member cat '("hob" "app" "floor" "heat" "leak")) (setq k 0.9 c 2.0))
        ((= cat "ac") (setq k 1.2 c 4.0))
        (T (setq k 1.2 c 4.0)))
  (setq x (cdr (assoc cat *gip:len-extra*)))
  (if (and (null x) (not (member cat '("light" "sock" "floor")))) (setq x (cdr (assoc "out" *gip:len-extra*))))
  (if (not (numberp x)) (setq x 0.0))
  (gip:ceil (* (+ c (* k s) x) 1.1)))

;; запас кабеля на приборы с планов. На подключение каждого светильника, выключателя, розетки — 0,3 м (расключение в коробке);
;; вывод на плане — 1 м; спуск от потолка к выключателю/розетке туда и обратно: при прокладке по потолку к каждой розетке и выключателю
;; кабель идёт вниз и снова вверх (2·(H − высота прибора)), при прокладке по полу к розеткам запас на подъём мал (2·0,3 м).
;; Количество делится поровну между линиями своей категории (какой прибор на какой линии — на плане не указано).
(defun gip:dev-extra (S lines / cnt nl ns nk nf no h route dS dK dF n k ng hs r)
  (setq cnt (vl-catch-all-apply '(lambda () (gip:plan-counts (gip:template-sheets))) nil))
  (if (vl-catch-all-error-p cnt) (setq cnt nil))
  (setq nl 0 ns 0 nk 0 nf 0 no 0)
  (foreach c cnt
    (setq k (car (car c)) n (cdr c))
    (cond ((= k "ЭОМ_Светильники_GIP") (setq nl (+ nl n)))
          ((= k "ЭОМ_Выключатели_GIP") (setq ns (+ ns n)))
          ((gip:starts (cadr (car c)) "Вывод") (setq no (+ no n)))
          ((= (gip:lower (cadr (car c))) "терморегулятор тп") (setq nf (+ nf n)))
          (T (setq nk (+ nk n)))))
  ;; высота потолков — средняя по помещениям из реестра, иначе 2,7 м
  (setq hs (vl-remove-if-not '(lambda (x) (> x 0.0)) (mapcar '(lambda (r) (nth 4 r)) (vl-catch-all-apply '(lambda () (gip:room-list)) nil))))
  (setq h (if (and hs (listp hs)) (/ (apply '+ hs) (length hs) 1000.0) 2.7))
  (setq route (gip:gn S "route" "Потолок")
        dS (* 2.0 (max 0.0 (- h 0.9)))
        dK (if (= route "Потолок") (* 2.0 (max 0.0 (- h 0.3))) 0.6)
        dF (if (= route "Потолок") (* 2.0 (max 0.0 (- h 1.5))) 0.6))
  (setq r nil)
  (foreach q (list (list "light" (+ (* nl 0.3) (* ns (+ 0.3 dS)))) (list "sock" (* nk (+ 0.3 dK))) (list "floor" (* nf (+ 0.3 dF))) (list "out" (* no 1.0)))
    (setq ng (length (vl-remove-if-not '(lambda (l) (if (= (car q) "out") (not (member (gip:g l "cat") '("light" "sock" "floor" "reserve"))) (= (gip:g l "cat") (car q)))) lines)))
    (if (and (> ng 0) (> (cadr q) 0.0)) (setq r (cons (cons (car q) (/ (cadr q) ng)) r))))
  r)

;; полный расчёт щита
(defun gip:board (s / lines devs flow rails all area v2)
  (setq v2 (= (gip:g s "v") 2))
  (setq lines (if v2 (gip:rows-lines s) (gip:build-lines s)) area (gip:gn s "area" 50.0))
  (setq *gip:len-extra* (vl-catch-all-apply 'gip:dev-extra (list s lines)))
  (if (vl-catch-all-error-p *gip:len-extra*) (setq *gip:len-extra* nil))
  (setq lines (mapcar '(lambda (l) (if (gip:g l "len") l (gip:s l "len" (gip:cable-len l area)))) lines))
  (setq devs (if v2 (gip:rows-order s (gip:rows-devices s lines)) (gip:apply-order s (gip:build-devices s lines))))
  (setq flow (gip:flow-rails s devs))
  (setq rails (gip:designate (gip:g flow "rails")))
  (setq all (apply 'append rails))
  (list (cons "lines" lines) (cons "devs" devs) (cons "rails" rails) (cons "all" all) (cons "cap" (gip:g flow "cap")) (cons "used" (gip:g flow "used")) (cons "box" (gip:g flow "box"))))
