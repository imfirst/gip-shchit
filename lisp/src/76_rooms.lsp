;;; ============================================================================
;;; Помещения: подложка плана дизайнера (стены / мебель) по центру листов планов, блоки номеров с атрибутами,
;;; реестр помещений в чертеже (словарь GIPROOMS) и экспликации (ACAD_TABLE), которые обновляются на месте.
;;; Данные готовит панель «Помещения» (файл TEMPPREFIX\gip_rooms_in.txt, по строке на объект):
;;;   (GIPROOMS 1 "имя" H_мм ширина_мм высота_мм)
;;;   (R номер "название" площадь_расчёт площадь_дизайнера H_мм x y)   x y — место номера, мм от левого нижнего угла подложки
;;;   (L k x y ...) / (C k ...) / (F k ...) — полилиния / замкнутая / заливка; k: 0 стены и окна, 1 двери и мебель
;;; Реестр: список (номер название S_расч S_диз H объём x y). Доступ для других программ ГИП:
;;;   (gip:room-list) (gip:room-get номер "NAME"|"AREA"|"AREAD"|"H"|"VOL")
;;; Блок номера NUM-POM_GIP_A: атрибуты NUM (виден), NAME, AREA, H, VOL (скрыты). Всё созданное помечено xdata GIPROOMS.
;;; ============================================================================
(setq *gip:rm-app* "GIPROOMS" *gip:rm-file* "gip_rooms_in.txt" *gip:rm-blk* "NUM-POM_GIP_A" *gip:rm-key* "GIPROOMS")

;; ---------------------------------------------------------------- реестр
(defun gip:room-list (/ s) (if (setq s (gip:dict-get *gip:rm-key*)) (read s)))
;; реестр + JSON для панели GIPPANEL (названия помещений -> подсказки для групп освещения и розеток)
(defun gip:room-put (l)
  (gip:dict-put *gip:rm-key* (vl-prin1-to-string l))
  (vl-catch-all-apply 'gip:rm-publish (list l)))
;; для панели: если реестр помещений уже есть в чертеже (импорт до обновления), а JSON ещё не опубликован
;; названия помещений из экспликации чертежа (если реестра нет): пары «№ — название» из первой таблицы-экспликации
(defun gip:rm-names-from-tables (/ ss i o nR nC k rr g no nm r)
  (setq r nil)
  (if (setq ss (ssget "_X" '((0 . "ACAD_TABLE"))))
    (progn
      (setq i 0)
      (while (and (null r) (< i (sslength ss)))
        (setq o (vlax-ename->vla-object (ssname ss i)) i (1+ i))
        (if (gip:rm-expl-table-p o)
          (progn
            (setq nR (vla-get-rows o) nC (vla-get-columns o) k (max 1 (/ nC 2)) rr 2)
            (while (< rr nR)
              (setq g 0)
              (while (< g k)
                (setq no (atoi (gip:rm-cell o rr (* 2 g))) nm (gip:rm-cell o rr (1+ (* 2 g))))
                (if (and (> no 0) (/= nm "") (not (assoc no r))) (setq r (cons (list no nm 0.0 0.0 0.0 0.0 nil nil) r)))
                (setq g (1+ g)))
              (setq rr (1+ rr))))))))
  (vl-sort r '(lambda (a b) (< (car a) (car b)))))
(defun gip:rm-publish-reg (/ l)
  (setq l (gip:room-list))
  (if (null l) (setq l (vl-catch-all-apply 'gip:rm-names-from-tables nil)))
  (if (vl-catch-all-error-p l) (setq l nil))
  (gip:rm-publish l)
  (princ (strcat "\nГИП: названий помещений для панели: " (itoa (length l))))
  (princ))
(defun gip:rm-publish (l / parts)
  (setq parts nil)
  (foreach r l
    (setq parts (cons (strcat "{\"no\":" (itoa (car r)) ",\"name\":" (gip:js-str (gip:u (cadr r))) ",\"area\":" (gip:js-num (nth 2 r)) ",\"h\":" (gip:js-num (nth 4 r)) "}") parts)))
  (gip:dict-put "GIPROOMSJSON" (strcat "[" (gip:join (reverse parts) ",") "]")))
(defun gip:room-get (no key / r)
  (if (setq r (assoc no (gip:room-list)))
    (cond ((= key "NAME") (nth 1 r)) ((= key "AREA") (nth 2 r)) ((= key "AREAD") (nth 3 r))
          ((= key "H") (nth 4 r)) ((= key "VOL") (nth 5 r)))))
;; периметр помещений, м: отдельный словарь (номер . периметр) — состав записи реестра не меняется
(defun gip:rm-perims (/ s) (if (setq s (gip:dict-get "GIPROOMSP")) (read s)))
(defun gip:rm-perim-put (no p / l)
  (setq l (vl-remove (assoc no (gip:rm-perims)) (gip:rm-perims)))
  (gip:dict-put "GIPROOMSP" (vl-prin1-to-string (cons (cons no (gip:rm-r2 p)) l))))
(defun gip:rm-perim-get (no / q) (if (setq q (assoc no (gip:rm-perims))) (cdr q) 0.0))
(defun gip:rm-pts-perim (pts / p a)
  (setq a 0.0 p (last pts))
  (foreach q pts (setq a (+ a (distance (list (car p) (cadr p)) (list (car q) (cadr q)))) p q))
  (/ a 1000.0))
(defun gip:rm-r2 (x) (/ (fix (+ (* x 100.0) 0.5)) 100.0))
(defun gip:rm-vol (area h) (gip:rm-r2 (* area (/ h 1000.0))))

;; строка от панели: ~uXXXX -> символ (AutoLISP-читалка эти последовательности не трогает)
(defun gip:rm-dec (s / r i p)
  (if (and (= (type s) 'STR) (vl-string-search "~u" s))
    (progn
      (setq r "" i 0)
      (while (setq p (vl-string-search "~u" s i))
        (setq r (strcat r (substr s (1+ i) (- p i)) (chr (gip:hex (substr s (+ p 3) 4))))
              i (+ p 6)))
      (strcat r (substr s (1+ i))))
    (gip:u s)))
;; ---------------------------------------------------------------- отчёт для панели
(defun gip:rm-report (ok msg / f p)
  (setq p (strcat (getvar "TEMPPREFIX") "gip_rooms_out.txt"))
  (if (setq f (open p "w"))
    (progn (write-line (if ok "ok" "error") f) (write-line (gip:plan-ascii msg) f) (close f))))
(defun gip:rm-json-str (s) (strcat "\"" (gip:repl (gip:repl (gip:plan-ascii s) "\\" "\\\\") "\"" "'") "\""))
(defun gip:rm-write-reg (/ f p fst r)
  (setq p (strcat (getvar "TEMPPREFIX") "gip_rooms_reg.txt") fst T)
  (if (setq f (open p "w"))
    (progn
      (princ "{\"type\":\"registry\",\"rooms\":[" f)
      (foreach r (gip:room-list)
        (if (not fst) (princ "," f))
        (setq fst nil)
        (princ (strcat "{\"no\":" (itoa (nth 0 r)) ",\"name\":" (gip:rm-json-str (nth 1 r))
                              ",\"h\":" (rtos (nth 4 r) 2 0) ",\"area\":" (rtos (nth 2 r) 2 2)
                              ",\"perim\":" (rtos (gip:rm-perim-get (nth 0 r)) 2 2) "}") f))
      (princ "]}" f) (close f))))

;; ---------------------------------------------------------------- блок номера с атрибутами
(defun gip:rm-style () (if (tblsearch "STYLE" "ls_200") "ls_200" "STANDARD"))
(defun gip:rm-attdef (tag prm val y h flags just / st)
  (setq st (gip:rm-style))
  (entmake (list '(0 . "ATTDEF") '(100 . "AcDbEntity") '(8 . "0") '(62 . 0) '(100 . "AcDbText")
                 (list 10 0.0 (float y) 0.0) (cons 40 (float h)) (cons 1 val) (cons 7 st) (cons 72 just) (list 11 0.0 (float y) 0.0)
                 '(100 . "AcDbAttributeDefinition") (cons 3 prm) (cons 2 tag) (cons 70 flags) (cons 74 (if (= just 1) 2 0)))))
;; круг R150 и номер высотой 150 по центру — как в динамическом NUM-POM_GIP
(defun gip:rm-ensure-block ()
  (if (not (tblsearch "BLOCK" *gip:rm-blk*))
    (progn
      (entmake (list '(0 . "BLOCK") (cons 2 *gip:rm-blk*) '(70 . 2) '(10 0.0 0.0 0.0)))
      (entmake '((0 . "CIRCLE") (100 . "AcDbEntity") (8 . "0") (62 . 0) (6 . "ByBlock") (100 . "AcDbCircle") (10 0.0 0.0 0.0) (40 . 150.0)))
      (gip:rm-attdef "NUM" "Номер помещения" "1" 0.0 150.0 0 1)
      (gip:rm-attdef "NAME" "Наименование" "" -330.0 100.0 1 0)
      (gip:rm-attdef "AREA" "Площадь, кв.м" "0" -480.0 100.0 1 0)
      (gip:rm-attdef "H" "Высота, мм" "0" -630.0 100.0 1 0)
      (gip:rm-attdef "VOL" "Объём, куб.м" "0" -780.0 100.0 1 0)
      (entmake '((0 . "ENDBLK")))))
  *gip:rm-blk*)

;; ---------------------------------------------------------------- метки и очистка
(defun gip:rm-tag (kind) (list (list -3 (list *gip:rm-app* (cons 1000 kind)))))
(defun gip:rm-tag-obj (obj kind / e)
  (setq e (vlax-vla-object->ename obj))
  (entmod (append (entget e) (gip:rm-tag kind)))
  e)
(defun gip:rm-clear (/ ss i n)
  (setq n 0)
  (if (setq ss (ssget "_X" (list (list -3 (list *gip:rm-app*)))))
    (progn (setq i 0) (while (< i (sslength ss)) (entdel (ssname ss i)) (setq i (1+ i) n (1+ n)))))
  n)
(defun gip:rm-blkname (pfx / i nm)
  (setq i 1)
  (while (tblsearch "BLOCK" (setq nm (strcat pfx (itoa i)))) (setq i (1+ i)))
  nm)
(defun gip:rm-insert (name x y lay kind / obj)
  (setq obj (vla-insertblock (gip:ms) (vlax-3d-point x y 0.0) name 1.0 1.0 1.0 0.0))
  (vla-put-layer obj (gip:layer lay))
  (gip:rm-tag-obj obj kind)
  obj)

;; ---------------------------------------------------------------- листы планов
;; любой лист шаблона с заголовком «План …» (вентиляция, силовые сети, освещение, ДСУП, ВиК…)
(defun gip:rm-sheets (/ r sh role)
  (setq r nil)
  (foreach sh (gip:plan-template-sheets)
    (setq role (gip:g sh "role"))
    (if (and (= (type role) 'STR) (wcmatch role "plan_*"))
      (setq r (cons (list (gip:g sh "F") (gip:g sh "title")) r))))
  (reverse r))

;; ---------------------------------------------------------------- экспликации
(defun gip:rm-pt (v) (vlax-safearray->list (vlax-variant-value v)))
(defun gip:rm-cell (tb r c / s)
  (setq s (vl-catch-all-apply 'vla-gettext (list tb r c)))
  (if (vl-catch-all-error-p s) "" (gip:mt-strip s)))
(defun gip:rm-expl-table-p (tb / s)
  (setq s (strcat (gip:rm-cell tb 0 0) " " (gip:rm-cell tb 1 0)))
  (if (or (gip:has (gip:lower s) "экспликация") (gip:has (gip:lower s) "помещен")) T nil))
(defun gip:rm-sw () (if (and (boundp '*gip:SW*) *gip:SW*) *gip:SW* 20960.5))
(defun gip:rm-shh () (if (and (boundp '*gip:SHH*) *gip:SHH*) *gip:SHH* 14850.0))
(defun gip:rm-in-frame (F p)
  (and (>= (car p) (- (car F) (gip:rm-sw) 100.0)) (<= (car p) (+ (car F) 100.0))
       (>= (cadr p) (- (cadr F) 100.0)) (<= (cadr p) (+ (cadr F) (gip:rm-shh) 100.0))))
;; найти экспликации листа: список vla-таблиц
(defun gip:rm-find-tables (F / ss i o r p)
  (setq r nil)
  (if (setq ss (ssget "_X" '((0 . "ACAD_TABLE"))))
    (progn
      (setq i 0)
      (while (< i (sslength ss))
        (setq o (vlax-ename->vla-object (ssname ss i)) i (1+ i)
              p (gip:rm-pt (vla-get-insertionpoint o)))
        (if (and (gip:rm-in-frame F p) (gip:rm-expl-table-p o)) (setq r (cons o r))))))
  r)
;; оформление ячейки (стиль текста, высота, выравнивание, inline-коды MText) берётся с образца исходной таблицы
(defun gip:rm-cell-fmt (tb rr cc / sty hgt raw pre i n ch go)
  (setq sty (vl-catch-all-apply 'vla-getcelltextstyle (list tb rr cc))
        hgt (vl-catch-all-apply 'vla-getcelltextheight (list tb rr cc))
        raw (vl-catch-all-apply 'vla-gettext (list tb rr cc)) pre "")
  (if (or (vl-catch-all-error-p sty) (/= (type sty) 'STR)) (setq sty nil))
  (if (or (vl-catch-all-error-p hgt) (not (numberp hgt))) (setq hgt nil))
  ;; ведущие коды форматирования («{\\fArial|b0;\\H150;» и т.п.) без самого текста
  (if (and (= (type raw) 'STR) (> (strlen raw) 3))
    (progn
      (setq i 1 n (strlen raw) go T)
      (while (and go (<= i n))
        (setq ch (substr raw i 1))
        (cond ((= ch "{") (setq i (1+ i)))
              ((and (= ch "\\") (< i n) (wcmatch (substr raw (1+ i) 1) "[fFHhCcQqWwTtAaLlOoKk]"))
               (if (setq ch (vl-string-search ";" raw i)) (setq i (+ ch 2)) (setq go nil)))
              (T (setq go nil))))
      (setq pre (substr raw 1 (1- i)))
      (if (not (and (> (strlen pre) 0) (vl-string-search ";" pre))) (setq pre ""))
      (if (and (/= pre "") (= (substr pre 1 1) "{") (/= (substr raw n 1) "}")) (setq pre ""))))
  (list sty hgt pre))
(defun gip:rm-fmt-ok (f) (and f (nth 0 f) (nth 1 f) (>= (nth 1 f) 20.0)))
;; лучший доступный образец: строка данных, иначе шапка, иначе ls_200 / 150 мм
(defun gip:rm-pick-fmt (tb rows cc / r f best)
  (foreach r rows (if (and (not best) (< r (vla-get-rows tb)) (gip:rm-fmt-ok (setq f (gip:rm-cell-fmt tb r cc)))) (setq best f)))
  (if best best (list (gip:rm-style) 150.0 "")))
(defun gip:rm-put-cell (tb rr cc txt fmt align / pre)
  (setq pre (nth 2 fmt))
  (vl-catch-all-apply 'vla-settext (list tb rr cc (if (/= pre "") (strcat pre txt (if (= (substr pre 1 1) "{") "}" "")) txt)))
  (if (nth 0 fmt) (vl-catch-all-apply 'vla-setcelltextstyle (list tb rr cc (nth 0 fmt))))
  (if (and (nth 1 fmt) (> (nth 1 fmt) 0.0)) (vl-catch-all-apply 'vla-setcelltextheight (list tb rr cc (nth 1 fmt))))
  (if align (vl-catch-all-apply 'vla-setcellalignment (list tb rr cc align))))
;; заполнить таблицу: заголовок и «шапка» остаются; строк ровно столько, сколько нужно; нижний левый угол остаётся на месте
(defun gip:rm-fill-table (tb rooms / nR nC k hdr start n need cur p bot idx rr cc g e rh fm0 fm1)
  (vl-catch-all-apply 'vla-put-horzcellmargin (list tb 50.0))   ; поле ячеек по горизонтали 50 (а не 1.5): текст не прилипает к границе
  (setq nR (vla-get-rows tb) nC (vla-get-columns tb) k (max 1 (/ nC 2)) n (length rooms) hdr 1)
  (setq rr 0)
  (while (< rr (min 4 nR))
    (if (or (gip:has (gip:rm-cell tb rr 0) "№") (= (strcase (gip:rm-cell tb rr 0)) "N")) (setq hdr rr rr 99))
    (setq rr (1+ rr)))
  (setq start (1+ hdr) need (max 1 (fix (/ (+ n k -1) k))) cur (- nR start)
        p (gip:rm-pt (vla-get-insertionpoint tb)) bot (- (cadr p) (vla-get-height tb))
        rh (vla-getrowheight tb (1- nR))
        fm0 (gip:rm-pick-fmt tb (list start hdr) 0) fm1 (gip:rm-pick-fmt tb (list start hdr) 1))
  (cond
    ((> need cur) (setq e (vl-catch-all-apply 'vla-insertrows (list tb (1- nR) rh (- need cur)))))
    ((< need cur) (setq e (vl-catch-all-apply 'vla-deleterows (list tb start (- cur need))))))
  (if (and e (vl-catch-all-error-p e)) (princ (strcat "\nГИП: строки таблицы: " (vl-catch-all-error-message e))))
  (setq nR (vla-get-rows tb))
  ;; очистить область данных
  (setq rr start)
  (while (< rr nR)
    (setq cc 0)
    (while (< cc nC) (vl-catch-all-apply 'vla-settext (list tb rr cc "")) (setq cc (1+ cc)))
    (setq rr (1+ rr)))
  (setq idx 0)
  (foreach r rooms
    (setq g (/ idx need) rr (+ start (rem idx need)))
    (gip:rm-put-cell tb rr (* 2 g) (itoa (car r)) fm0 5)          ; номер: по центру
    (gip:rm-put-cell tb rr (1+ (* 2 g)) (gip:u (cadr r)) fm1 4)   ; название: слева по середине
    (setq idx (1+ idx)))
  (vla-put-insertionpoint tb (vlax-3d-point (car p) (+ bot (vla-get-height tb)) 0.0))
  T)
;; новая таблица (если на листе её не было): нижний левый угол — внутренний угол рамки, как в шаблоне
(defun gip:rm-any-table (/ ss i o r)
  (setq r nil)
  (if (setq ss (ssget "_X" '((0 . "ACAD_TABLE"))))
    (progn (setq i 0)
      (while (and (not r) (< i (sslength ss)))
        (setq o (vlax-ename->vla-object (ssname ss i)) i (1+ i))
        (if (gip:rm-expl-table-p o) (setq r o)))))
  r)
(defun gip:rm-new-table (F rooms / n tb x y h src)
  (setq n (length rooms) h (* 150.0 (+ n 2)) x (- (car F) (- (gip:rm-sw) 500.0)) y (+ (cadr F) 500.0 h))
  ;; оформление (стиль таблицы, шрифт, высота текста) копируется с уже существующей экспликации чертежа
  (setq src (vl-catch-all-apply 'gip:rm-any-table nil))
  (if (or (vl-catch-all-error-p src) (null src)) (setq src nil))
  (if src
    (progn
      (setq tb (vla-copy src))
      ;; у копии не должно быть метки заготовки
      (vl-catch-all-apply 'entmod (list (list (cons -1 (vlax-vla-object->ename tb)) (list -3 (list *gip:rm-app*)))))
      (vla-put-insertionpoint tb (vlax-3d-point x y 0.0)))
    (progn
      (setq tb (vla-addtable (gip:ms) (vlax-3d-point x y 0.0) (+ n 2) 2 150.0 2000.0))
      (vla-setcolumnwidth tb 0 631.58) (vla-setcolumnwidth tb 1 3368.42)
      (vla-settext tb 0 0 "Экспликация помещений")
      (vl-catch-all-apply 'vla-mergecells (list tb 0 0 0 1))
      (vla-settext tb 1 0 "№")
      (vla-settext tb 1 1 "Наименование помещения")))
  (vla-put-layer tb (if src (vla-get-layer src) (gip:layer "GIP_Экспликация помещений")))
  ;; низ таблицы = внутренний угол рамки; fill-table сохраняет нижний левый угол, поэтому задаём его до заполнения
  (vla-put-insertionpoint tb (vlax-3d-point x (+ (cadr F) 500.0 (vla-get-height tb)) 0.0))
  (gip:rm-fill-table tb rooms)
  tb)
;; ---------------------------------------------------------------- таблица площадей рядом с заготовкой
;; №, название, S дизайнера, S измеренная, расхождение, H, периметр. Отсюда берутся площади, высоты и периметры для расчётов.
(defun gip:rm-area-tables (/ ss i r)
  (setq r nil)
  (if (setq ss (ssget "_X" (list '(0 . "ACAD_TABLE") (list -3 (list *gip:rm-app*)))))
    (progn (setq i 0)
      (while (< i (sslength ss))
        (if (= (gip:rm-kind (ssname ss i)) "SA") (setq r (cons (ssname ss i) r)))
        (setq i (1+ i)))))
  r)
(defun gip:rm-f1 (x) (if (and (numberp x) (> x 0.0)) (rtos x 2 1) "—"))
(defun gip:rm-area-table (rooms / F0 old pt n tb r rr fm c w)
  (setq F0 (gip:rm-stage-f 0)
        pt (list (+ (car F0) 1500.0) (+ (cadr F0) (gip:rm-shh)) 0.0))
  ;; прежняя таблица: удаляем, положение сохраняем
  (foreach e (gip:rm-area-tables)
    (setq pt (gip:rm-pt (vla-get-insertionpoint (vlax-ename->vla-object e))))
    (entdel e))
  (setq n (length rooms)
        tb (vla-addtable (gip:ms) (vlax-3d-point (car pt) (cadr pt) 0.0) (+ n 2) 7 400.0 1000.0))
  (setq w '(900.0 3600.0 1700.0 1700.0 1300.0 1400.0 1500.0) c 0)
  (foreach x w (vla-setcolumnwidth tb c x) (setq c (1+ c)))
  (vl-catch-all-apply 'vla-put-horzcellmargin (list tb 50.0))
  (vla-settext tb 0 0 "Площади помещений")
  (vl-catch-all-apply 'vla-mergecells (list tb 0 0 0 6))
  (setq c 0)
  (foreach h '("№" "Наименование" "S дизайнера, м²" "S измеренная, м²" "Откл., %" "H, мм" "Периметр, м")
    (vla-settext tb 1 c h) (setq c (1+ c)))
  (setq rr 2)
  (foreach r rooms
    (vla-settext tb rr 0 (itoa (car r)))
    (vla-settext tb rr 1 (gip:u (cadr r)))
    (vla-settext tb rr 2 (gip:rm-f1 (nth 3 r)))
    (vla-settext tb rr 3 (gip:rm-f1 (nth 2 r)))
    (vla-settext tb rr 4 (if (and (> (nth 2 r) 0.0) (> (nth 3 r) 0.0)) (rtos (* 100.0 (/ (- (nth 2 r) (nth 3 r)) (nth 3 r))) 2 1) "—"))
    (vla-settext tb rr 5 (rtos (nth 4 r) 2 0))
    (vla-settext tb rr 6 (gip:rm-f1 (gip:rm-perim-get (car r))))
    (setq rr (1+ rr)))
  ;; шрифт и размер — как у экспликации (ls_200, 150), поле по горизонтали 50
  (setq rr 0)
  (while (< rr (+ n 2))
    (setq c 0)
    (while (< c 7)
      (vl-catch-all-apply 'vla-setcelltextstyle (list tb rr c (gip:rm-style)))
      (vl-catch-all-apply 'vla-setcelltextheight (list tb rr c 150.0))
      (vl-catch-all-apply 'vla-setcellalignment (list tb rr c (if (and (>= rr 2) (= c 1)) 4 5)))
      (setq c (1+ c)))
    (setq rr (1+ rr)))
  (vla-put-layer tb (gip:layer "GIP_Заготовка"))
  (gip:rm-tag-obj tb "SA")
  tb)
;; правки в таблице площадей (название, высота) -> реестр
(defun gip:rm-read-area-table (rooms / e tb nR rr no nm h r)
  (if (setq e (car (gip:rm-area-tables)))
    (progn
      (setq tb (vlax-ename->vla-object e) nR (vla-get-rows tb) rr 2)
      (while (< rr nR)
        (setq no (atoi (gip:rm-cell tb rr 0)) nm (gip:rm-cell tb rr 1) h (atof (gip:rm-cell tb rr 5)))
        (if (and (> no 0) (setq r (assoc no rooms)))
          (setq rooms (subst (list (nth 0 r) (if (/= nm "") nm (nth 1 r)) (nth 2 r) (nth 3 r) (if (> h 0.0) h (nth 4 r))
                                   (gip:rm-vol (nth 2 r) (if (> h 0.0) h (nth 4 r))) (nth 6 r) (nth 7 r))
                             r rooms)))
        (setq rr (1+ rr)))))
  rooms)
(defun gip:rm-sync-tables (sheets rooms / sh tbs nT nN)
  (setq nT 0 nN 0)
  (foreach sh sheets
    (setq tbs (vl-catch-all-apply 'gip:rm-find-tables (list (car sh))))
    (if (vl-catch-all-error-p tbs) (setq tbs nil))
    (if tbs
      (foreach tb tbs (if (not (vl-catch-all-error-p (vl-catch-all-apply 'gip:rm-fill-table (list tb rooms)))) (setq nT (1+ nT))))
      (if (not (vl-catch-all-error-p (vl-catch-all-apply 'gip:rm-new-table (list (car sh) rooms)))) (setq nN (1+ nN)))))
  (if (gip:rm-kind-refs "SW")
    (progn (vl-catch-all-apply 'gip:rm-stage-table (list rooms))
           (vl-catch-all-apply 'gip:rm-area-table (list rooms))))
  (list nT nN))

;; ---------------------------------------------------------------- блоки номеров: атрибуты из реестра
(defun gip:rm-room-atts (r)
  (list (cons "NUM" (itoa (nth 0 r))) (cons "NAME" (gip:u (nth 1 r))) (cons "AREA" (rtos (nth 2 r) 2 1))
        (cons "H" (rtos (nth 4 r) 2 0)) (cons "VOL" (rtos (nth 5 r) 2 2))))
(defun gip:rm-eff (e / nm)
  (setq nm (vl-catch-all-apply 'vlax-get (list (vlax-ename->vla-object e) 'EffectiveName)))
  (if (= (type nm) 'STR) nm ""))
;; блок номера: динамический NUM-POM_GIP (номер — состояние видимости, как в шаблоне), если он есть в чертеже и номеров не больше 15;
;; иначе запасной NUM-POM_GIP_A с атрибутами
(defun gip:rm-dyn-p (rooms)
  (and (tblsearch "BLOCK" "NUM-POM_GIP") (vl-every '(lambda (r) (<= 1 (car r) 15)) rooms)))
(defun gip:rm-marker-blk (rooms) (if (gip:rm-dyn-p rooms) "NUM-POM_GIP" (gip:rm-ensure-block)))
(defun gip:rm-num-refs (/ ss i r e nm)
  (setq r nil)
  (if (setq ss (ssget "_X" '((0 . "INSERT"))))
    (progn (setq i 0)
      (while (< i (sslength ss))
        (setq e (ssname ss i) i (1+ i) nm (strcase (gip:rm-eff e)))
        (if (or (= nm "NUM-POM_GIP") (= nm (strcase *gip:rm-blk*))) (setq r (cons e r))))))
  (reverse r))
(defun gip:rm-att-val (obj tag / atts v)
  (setq atts (vl-catch-all-apply 'vlax-invoke (list obj 'GetAttributes)) v "")
  (if (not (vl-catch-all-error-p atts))
    (foreach a atts (if (= (strcase (vlax-get a 'TagString)) tag) (setq v (vlax-get a 'TextString)))))
  v)
;; номер помещения из блока (динамический: значение списка видимости; с атрибутами: NUM)
(defun gip:rm-num (obj / nm n props)
  (setq nm (vl-catch-all-apply 'vlax-get (list obj 'EffectiveName)) n 0)
  (if (and (= (type nm) 'STR) (= (strcase nm) "NUM-POM_GIP"))
    (progn
      (setq props (vl-catch-all-apply 'vlax-invoke (list obj 'GetDynamicBlockProperties)))
      (if (not (vl-catch-all-error-p props))
        (foreach p props
          (if (and (= n 0) (wcmatch (strcase (vlax-get p 'PropertyName)) "VISIBILITY*")) (setq n (atoi (vlax-get p 'Value)))))))
    (setq n (atoi (gip:rm-att-val obj "NUM"))))
  n)
;; заполнить блок номера данными помещения
(defun gip:rm-fill-marker (obj r / nm)
  (setq nm (vl-catch-all-apply 'vlax-get (list obj 'EffectiveName)))
  (if (and (= (type nm) 'STR) (= (strcase nm) "NUM-POM_GIP"))
    (gip:set-vis obj "NUM-POM_GIP" (itoa (car r)))
    (gip:set-atts obj (gip:rm-room-atts r))))
(defun gip:rm-sync-blocks (rooms / e obj no r n)
  (setq n 0)
  (foreach e (gip:rm-num-refs)
    (setq obj (vlax-ename->vla-object e) no (gip:rm-num obj))
    (if (setq r (assoc no rooms)) (progn (gip:rm-fill-marker obj r) (setq n (1+ n)))))
  n)

;; ---------------------------------------------------------------- заготовка над альбомом
;; Импорт кладёт подложку, номера, экспликацию и листы электрики в отдельные рамки НАД альбомом (kind S*):
;; рамка 0 — подложка и номера, рамки 1.. — листы электрики. Оттуда команда GIPROOMSDIST раскладывает подложку по листам планов.
(defun gip:rm-album-box (/ ss i e o nm F x0 y1 n)
  (setq n 0 x0 nil y1 nil)
  (if (setq ss (ssget "_X" '((0 . "INSERT"))))
    (progn
      (setq i 0)
      (while (< i (sslength ss))
        (setq e (ssname ss i) i (1+ i) o (vlax-ename->vla-object e)
              nm (vl-catch-all-apply 'vlax-get (list o 'EffectiveName)))
        (if (and (= (type nm) 'STR) (= nm "А3-GIP-ALBOM"))
          (progn
            (setq F (cdr (assoc 10 (entget e))) n (1+ n))
            (if (or (null x0) (< (- (car F) (gip:rm-sw)) x0)) (setq x0 (- (car F) (gip:rm-sw))))
            (if (or (null y1) (> (+ (cadr F) (gip:rm-shh)) y1)) (setq y1 (+ (cadr F) (gip:rm-shh)))))))))
  (if (> n 0) (list x0 y1) (list 0.0 0.0)))
;; правый нижний угол рамки заготовки номер i
(defun gip:rm-stage-f (i / bx)
  (setq bx (gip:rm-album-box))
  (list (+ (car bx) (gip:rm-sw) (* i (+ (gip:rm-sw) 2000.0))) (+ (cadr bx) 29000.0)))   ; заготовки на 26000 мм выше прежнего положения
;; Положение плана на листе (относительно правого нижнего угла рамки А3): внутренняя рамка x -19960..-250,
;; штамп справа внизу (до y=3000), название листа у верхней границы (y 14200..14450).
;; План ставится в полосе между штампом и названием; большой план прижимается к верху (название потом отодвигается).
(defun gip:rm-plan-pos (W H / xl xr cx cy)
  (setq xl -19760.0 xr -450.0 cx (car *gip:plan-at*))
  (setq cx (if (<= W (- xr xl)) (max (+ xl (/ W 2.0)) (min (- xr (/ W 2.0)) cx)) (+ xl (/ W 2.0))))
  (setq cy (if (<= H 10600.0) 8600.0 (- 14300.0 (/ H 2.0))))
  (list cx cy))
(defun gip:rm-plan-org (F W H / c)
  (setq c (gip:rm-plan-pos W H))
  (list (+ (car F) (- (car c) (/ W 2.0))) (+ (cadr F) (- (cadr c) (/ H 2.0)))))
(defun gip:rm-stage-frame (F title / x0 y0 x1 y1)
  (setq x0 (- (car F) (gip:rm-sw)) y0 (cadr F) x1 (car F) y1 (+ (cadr F) (gip:rm-shh)))
  (gip:layer "GIP_Заготовка")
  (entmake (append (list '(0 . "LWPOLYLINE") '(100 . "AcDbEntity") '(8 . "GIP_Заготовка") '(62 . 7) '(100 . "AcDbPolyline") '(90 . 4) '(70 . 1)
                         (list 10 x0 y0) (list 10 x1 y0) (list 10 x1 y1) (list 10 x0 y1))
                   (gip:rm-tag "S")))
  (entmake (append (list '(0 . "TEXT") '(8 . "GIP_Заготовка") '(62 . 7) (list 10 (+ x0 500.0) (- y1 800.0) 0.0) '(40 . 400.0) (cons 1 title) (cons 7 (gip:rm-style)))
                   (gip:rm-tag "S"))))
(defun gip:rm-kind (e / x)
  (setq x (cdr (assoc *gip:rm-app* (cdr (assoc -3 (entget e (list *gip:rm-app*)))))))
  (if x (cdr (assoc 1000 x))))
(defun gip:rm-kind-refs (kind / ss i r)
  (setq r nil)
  (if (setq ss (ssget "_X" (list '(0 . "INSERT") (list -3 (list *gip:rm-app*)))))
    (progn (setq i 0)
      (while (< i (sslength ss))
        (if (= (gip:rm-kind (ssname ss i)) kind) (setq r (cons (ssname ss i) r)))
        (setq i (1+ i)))))
  (reverse r))
(defun gip:rm-layname (s)
  (foreach ch '("<" ">" "/" "\\" ":" ";" "?" "*" "|" "," "=" "`" "\"") (setq s (gip:repl s ch " ")))
  s)

(defun gip:rm-pairs (l / r)
  (setq r nil)
  (while (cdr l) (setq r (cons (list (float (car l)) (float (cadr l))) r) l (cddr l)))
  (reverse r))
(defun gip:rm-poly-area (pts / a p q)
  (setq a 0.0 p (last pts))
  (foreach q pts (setq a (+ a (- (* (car p) (cadr q)) (* (car q) (cadr p)))) p q))
  (abs (/ a 2.0)))
;; ---------------------------------------------------------------- импорт из панели
(defun gip:rm-import (fn / pl q pts a f l it head W H hdef rooms gw gf gj ge en blkJ blkW blkF blkE sh F0 org n nB e obj r msg k i ent title)
  (if (not (and fn (findfile fn) (setq f (open fn "r"))))
    (progn (gip:rm-report nil "нет файла от панели") nil)
    (progn
      (regapp *gip:rm-app*)
      (setq head (read (read-line f)))
      (if (not (and (listp head) (eq (car head) 'GIPROOMS)))
        (progn (close f) (gip:rm-report nil "файл не распознан") nil)
        (progn
          (setq hdef (nth 3 head) W (nth 4 head) H (nth 5 head) rooms nil gw nil gf nil gj nil ge nil en nil pl nil nB 0)
          (while (setq l (read-line f))
            (if (/= l "")
              (progn
                (setq it (read l))
                (cond
                  ((and (eq (car it) 'J) (= (length it) 5)) (setq gj (cons it gj)))
                  ((and (eq (car it) 'P) (numberp (nth 1 it)) (> (length it) 7)) (setq pl (cons it pl)))
                  ((and (eq (car it) 'EH) (numberp (nth 1 it))) (setq en (cons (cons (fix (nth 1 it)) (gip:rm-dec (nth 2 it))) en)))
                  ((and (member (car it) '(L C F LK CK FK TX)) (numberp (cadr it)))
                   (setq k (fix (cadr it)))
                   (cond ((= k 0) (setq gw (cons it gw)))
                         ((= k 1) (setq gf (cons it gf)))
                         ((>= k 10)
                          (if (setq e (assoc (- k 10) ge)) (setq ge (subst (cons (car e) (cons it (cdr e))) e ge)) (setq ge (cons (list (- k 10) it) ge))))))
                  ((and (eq (car it) 'R) (numberp (nth 1 it)) (= (type (nth 2 it)) 'STR))
                   (setq rooms (cons (list (nth 1 it) (gip:rm-dec (nth 2 it)) (float (nth 3 it)) (float (nth 4 it)) (float (nth 5 it))
                                           (gip:rm-vol (float (nth 3 it)) (float (nth 5 it))) (nth 6 it) (nth 7 it)) rooms)))))))
          (close f)
          (vl-file-delete fn)
          (setq rooms (reverse rooms))
          (cond
            ((null rooms) (gip:rm-report nil "В файле нет помещений") nil)
            (T
             (gip:rm-clear)
             (setq blkW (gip:rm-blkname "GIP_RM_W_") blkF (gip:rm-blkname "GIP_RM_F_"))
             (entmake (list '(0 . "BLOCK") (cons 2 blkW) '(70 . 0) '(10 0.0 0.0 0.0)))
             (foreach it (reverse gw) (gip:plan-ent it))
             (entmake '((0 . "ENDBLK")))
             (entmake (list '(0 . "BLOCK") (cons 2 blkF) '(70 . 0) '(10 0.0 0.0 0.0)))
             (foreach it (reverse gf) (gip:plan-ent it))
             (entmake '((0 . "ENDBLK")))
             (setq blkJ (gip:rm-blkname "GIP_RM_J_"))
             (entmake (list '(0 . "BLOCK") (cons 2 blkJ) '(70 . 0) '(10 0.0 0.0 0.0)))
             (foreach it gj (entmake (list '(0 . "LINE") '(8 . "0") (cons 10 (list (float (nth 1 it)) (float (nth 2 it)) 0.0)) (cons 11 (list (float (nth 3 it)) (float (nth 4 it)) 0.0)))))
             (entmake '((0 . "ENDBLK")))
             (if (not (gip:rm-dyn-p rooms)) (gip:rm-ensure-block))
             ;; рамка 0 заготовки: подложка по центру, как на листах планов
             (setq F0 (gip:rm-stage-f 0) org (gip:rm-plan-org F0 W H))
             (gip:rm-stage-frame F0 (strcat "Заготовка: подложка и номера помещений"
                                           (if (/= (nth 2 head) "") (strcat " - " (gip:rm-dec (nth 2 head))) "")))
             (setq obj (gip:rm-insert blkW (car org) (cadr org) "GIP_Подложка" "SW"))
             (setq e (vlax-vla-object->ename obj))
             (entmod (append (entget e) (list (list -3 (list *gip:rm-app* (cons 1000 "SW") (list 1010 (car org) (cadr org) 0.0) (cons 1040 W) (cons 1040 H))))))
             (gip:rm-insert blkF (car org) (cadr org) "GIP_Подложка" "SF")
             (if gj (gip:rm-insert blkJ (car org) (cadr org) "GIP_ПОМ_ПЕРЕМЫЧКА" "SJ"))
             (foreach r rooms
               (if (and (numberp (nth 6 r)) (numberp (nth 7 r)))
                 (progn
                   (setq obj (gip:rm-insert (gip:rm-marker-blk rooms) (+ (car org) (nth 6 r)) (+ (cadr org) (nth 7 r)) "GIP_Номера помещений" "SN"))
                   (gip:rm-fill-marker obj r)
                   (setq nB (1+ nB)))))
             ;; контуры помещений, найденные панелью: скрытый слой, площадь по контуру (без BOUNDARY)
             (if pl
               (progn
                 (gip:layer "GIP_ПОМ_КОНТУР") (gip:rm-noplot "GIP_ПОМ_КОНТУР")
                 (setq rooms
                       (mapcar '(lambda (r)
                                  (if (setq q (vl-some '(lambda (x) (if (= (fix (nth 1 x)) (car r)) x)) pl))
                                    (progn
                                      (setq pts (gip:rm-pairs (cddr q)) a (gip:rm-r2 (/ (gip:rm-poly-area pts) 1000000.0)))
                                      (gip:rm-perim-put (car r) (gip:rm-pts-perim pts))
                                      (gip:rm-make-contour2 pts (car org) (cadr org) "SC")
                                      (list (nth 0 r) (nth 1 r) a (nth 3 r) (nth 4 r) (gip:rm-vol a (nth 4 r)) (nth 6 r) (nth 7 r)))
                                    r))
                               rooms))
                 (gip:rm-sync-blocks rooms)))
             ;; листы электрики: каждый — отдельный блок в своей рамке справа от основной (то же положение относительно рамки)
             (setq i 0)
             (foreach ent (reverse ge)
               (setq title (if (assoc (car ent) en) (cdr (assoc (car ent) en)) (strcat "Лист " (itoa (1+ (car ent))))))
               (setq blkE (gip:rm-blkname "GIP_RM_E_"))
               (entmake (list '(0 . "BLOCK") (cons 2 blkE) '(70 . 0) '(10 0.0 0.0 0.0)))
               (foreach it (reverse (cdr ent)) (gip:rm-ent it))
               (entmake '((0 . "ENDBLK")))
               (setq i (1+ i) sh (gip:rm-stage-f i))
               (gip:rm-stage-frame sh (strcat "Заготовка: " title))
               (gip:rm-insert blkE (car (gip:rm-plan-org sh W H)) (cadr (gip:rm-plan-org sh W H)) (strcat "GIP_Подложка " (gip:rm-layname title)) "SE"))
             (gip:room-put rooms)
             (setq n (gip:rm-stage-table rooms))
             (setq msg (strcat "заготовка над альбомом: помещений " (itoa (length rooms)) ", блоков номеров " (itoa nB)
                               (if ge (strcat ", листов электрики " (itoa (length ge))) "")
                               ". Передвиньте номера при необходимости, затем «Разложить по листам планов»."))
             (princ (strcat "\nГИП: помещения - " msg))
             (gip:rm-report T msg)
             T)))))))


;; элемент листа электрики: LK/CK/FK — с истинным цветом оригинала (rgb целым числом), L/C/F — по умолчанию
(defun gip:rm-ent (it / tg)
  (setq tg (vl-symbol-name (car it)))
  (if (eq (car it) 'TX)
    ;; (TX k x y h rot "str") — текст листа электрики
    (vl-catch-all-apply 'entmake
      (list (list '(0 . "TEXT") '(8 . "0") '(62 . 7)
                  (list 10 (float (nth 2 it)) (float (nth 3 it)) 0.0)
                  (cons 40 (float (nth 4 it)))
                  (cons 1 (gip:rm-dec (nth 6 it)))
                  (cons 50 (* (float (nth 5 it)) (/ pi 180.0))))))
  (if (and (= (strlen tg) 2) (= (substr tg 2 1) "K") (numberp (nth 2 it)))
    (progn
      (setq *gip:plan-rgb* (fix (nth 2 it)))
      (vl-catch-all-apply 'gip:plan-ent (list (cons (read (substr tg 1 1)) (cons (cadr it) (cdddr it)))))
      (setq *gip:plan-rgb* nil))
    (gip:plan-ent it))))
;; экспликация в рамке заготовки: обновить на месте или создать (по образцу существующей)
(defun gip:rm-stage-table (rooms / F0 tbs tb n)
  (setq F0 (gip:rm-stage-f 0) n 0)
  (setq tbs (vl-catch-all-apply 'gip:rm-find-tables (list F0)))
  (if (vl-catch-all-error-p tbs) (setq tbs nil))
  (if tbs
    (foreach tb tbs (if (not (vl-catch-all-error-p (vl-catch-all-apply 'gip:rm-fill-table (list tb rooms)))) (setq n (1+ n))))
    (progn
      (setq tb (vl-catch-all-apply 'gip:rm-new-table (list F0 rooms)))
      (if (not (vl-catch-all-error-p tb)) (progn (gip:rm-tag-obj tb "ST") (setq n 1)))))
  n)

;; ---------------------------------------------------------------- разложить заготовку по листам планов
(setq *gip:rm-st* nil)
;; правки экспликации в заготовке (названия) -> реестр
(defun gip:rm-read-stage-table (rooms / tbs tb nR nC k rr g no nm r n)
  (setq n 0 tbs (vl-catch-all-apply 'gip:rm-find-tables (list (gip:rm-stage-f 0))))
  (if (and (not (vl-catch-all-error-p tbs)) tbs)
    (progn
      (setq tb (car tbs) nR (vla-get-rows tb) nC (vla-get-columns tb) k (max 1 (/ nC 2)))
      (setq rr 2)
      (while (< rr nR)
        (setq g 0)
        (while (< g k)
          (setq no (atoi (gip:rm-cell tb rr (* 2 g))) nm (gip:rm-cell tb rr (1+ (* 2 g))))
          (if (and (> no 0) (/= nm "") (setq r (assoc no rooms)) (/= nm (nth 1 r)))
            (setq rooms (subst (cons (nth 0 r) (cons nm (cddr r))) r rooms) n (1+ n)))
          (setq g (1+ g)))
        (setq rr (1+ rr)))))
  rooms)
;; название листа (текст у верхней границы рамки)
(defun gip:rm-sheet-title (F / ss i e p r best)
  (setq r nil best 1e9)
  (if (setq ss (ssget "_C" (list (- (car F) (gip:rm-sw)) (+ (cadr F) 13900.0)) (list (car F) (+ (cadr F) (gip:rm-shh))) '((0 . "TEXT,MTEXT"))))
    (progn
      (setq i 0)
      (while (< i (sslength ss))
        (setq e (ssname ss i) i (1+ i) p (cdr (assoc 10 (entget e))))
        (if (and (>= (- (cadr p) (cadr F)) 13900.0) (< (abs (- (car p) (car F) -10105.0)) best))
          (setq r e best (abs (- (car p) (car F) -10105.0)))))))
  r)
;; если план налезает на название листа — переносим название в свободное место слева от штампа
(defun gip:rm-fix-title (F org W H / e obj mn mx cx cy w h x0 y0 dx dy hit)
  (setq e (gip:rm-sheet-title F))
  (if e
    (progn
      (setq obj (vlax-ename->vla-object e))
      (vla-getboundingbox obj 'mn 'mx)
      (setq mn (vlax-safearray->list mn) mx (vlax-safearray->list mx)
            w (- (car mx) (car mn)) h (- (cadr mx) (cadr mn)))
      (if (and (< (car mn) (+ (car org) W 150.0)) (> (car mx) (- (car org) 150.0))
               (< (cadr mn) (+ (cadr org) H 150.0)) (> (cadr mx) (- (cadr org) 150.0)))
        (progn
          ;; кандидат: слева внизу, левее штампа (штамп начинается с x = -9500)
          (setq x0 (+ (car F) -14730.0 (- (/ w 2.0))) y0 (+ (cadr F) 400.0))
          (if (not (and (< x0 (+ (car org) W 150.0)) (> (+ x0 w) (- (car org) 150.0))
                        (< y0 (+ (cadr org) H 150.0)) (> (+ y0 h) (- (cadr org) 150.0))))
            (progn
              (vla-move obj (vlax-3d-point (car mn) (cadr mn) 0.0) (vlax-3d-point x0 y0 0.0))
              T)))))))
;; скопировать содержимое рамки заготовки (всё, что есть: подложка, номера, ваши правки) на лист
(defun gip:rm-copy-stage (F0 F orgS org W H rooms / ss i e ed kind obj o2 nn typ)
  (setq nn 0 ss (ssget "_C" (list (- (car F0) (gip:rm-sw)) (cadr F0)) (list (car F0) (+ (cadr F0) (gip:rm-shh)))))
  (if ss
    (progn
      (setq i 0)
      (while (< i (sslength ss))
        (setq e (ssname ss i) i (1+ i) ed (entget e) typ (cdr (assoc 0 ed)) kind (cond ((gip:rm-kind e)) (T "U")))
        (if (not (or (member kind '("S" "ST")) (= typ "ACAD_TABLE")))
          (progn
            (setq obj (vlax-ename->vla-object e) o2 (vla-copy obj))
            (vla-move o2 (vlax-3d-point (car orgS) (cadr orgS) 0.0) (vlax-3d-point (car org) (cadr org) 0.0))
            (setq kind (if (= (substr kind 1 1) "S") (substr kind 2) kind))
            (if (= kind "W")
              (entmod (append (entget (vlax-vla-object->ename o2)) (list (list -3 (list *gip:rm-app* (cons 1000 "W") (list 1010 (car org) (cadr org) 0.0) (cons 1040 W) (cons 1040 H))))))
              (gip:rm-tag-obj o2 kind))
            (if (= kind "N") (setq nn (1+ nn))))))))
  nn)
;; запасной путь (без выбора рамкой): только блоки подложки и номера
(defun gip:rm-copy-stage-refs (orgS org W H rooms / ents e ed kind pt obj r nn nm)
  (setq nn 0 ents (append (gip:rm-kind-refs "SW") (gip:rm-kind-refs "SF") (gip:rm-kind-refs "SJ") (gip:rm-kind-refs "SN")))
  (foreach e ents
    (setq ed (entget e) kind (substr (gip:rm-kind e) 2)
          pt (list (+ (car (cdr (assoc 10 ed))) (- (car org) (car orgS))) (+ (cadr (cdr (assoc 10 ed))) (- (cadr org) (cadr orgS)))))
    (setq obj (gip:rm-insert (if (= (setq nm (gip:rm-eff e)) "") (cdr (assoc 2 ed)) nm) (car pt) (cadr pt) (cdr (assoc 8 ed)) kind))
    (cond
      ((= kind "W")
       (entmod (append (entget (vlax-vla-object->ename obj)) (list (list -3 (list *gip:rm-app* (cons 1000 "W") (list 1010 (car org) (cadr org) 0.0) (cons 1040 W) (cons 1040 H)))))))
      ((= kind "N")
       (if (setq r (assoc (gip:rm-num (vlax-ename->vla-object e)) rooms))
         (gip:rm-fill-marker obj r))
       (setq nn (1+ nn)))))
  nn)
(defun gip:rm-dist-run (/ sw0 xd orgS W H sheets rooms sh org e obj no r n nn nt F0 res)
  (setq sw0 (car (gip:rm-kind-refs "SW")))
  (cond
    ((null sw0) (gip:rm-report nil "Нет заготовки: сначала «Вставить в заготовку над альбомом»."))
    ((null (setq sheets (gip:rm-sheets))) (gip:rm-report nil "Не найдены листы планов (рамки А3-GIP-ALBOM с заголовком «План …»)."))
    (T
     (setq xd (gip:rm-xd sw0) orgS (car xd) W (cadr xd) H (caddr xd) rooms (gip:room-list) F0 (gip:rm-stage-f 0))
     ;; что вы поправили в заготовке — то и раскладывается: названия из экспликации заготовки, положение номеров, номера/атрибуты блоков
     (setq rooms (gip:rm-read-area-table (gip:rm-read-stage-table rooms)))
     (foreach e (gip:rm-kind-refs "SN")
       (setq obj (vlax-ename->vla-object e) no (gip:rm-num obj))
       (if (setq r (assoc no rooms))
         (setq rooms (subst (append (list (nth 0 r) (nth 1 r) (nth 2 r) (nth 3 r) (nth 4 r) (nth 5 r))
                                    (list (- (car (cdr (assoc 10 (entget e)))) (car orgS)) (- (cadr (cdr (assoc 10 (entget e)))) (cadr orgS))))
                            r rooms))))
     (gip:room-put rooms)
     (gip:rm-sync-blocks rooms)
     ;; убрать прежние копии на листах (но не заготовку)
     (foreach e (gip:rm-tagged-all)
       (if (not (wcmatch (strcat (cond ((gip:rm-kind e)) (T "")) "") "S*")) (entdel e)))
     (setq n 0 nn 0 nt 0)
     (foreach sh sheets
       (setq org (gip:rm-plan-org (car sh) W H))
       (setq res (vl-catch-all-apply 'gip:rm-copy-stage (list F0 (car sh) orgS org W H rooms)))
       (if (vl-catch-all-error-p res) (setq res (gip:rm-copy-stage-refs orgS org W H rooms)))
       (setq nn res)
       (if (not (vl-catch-all-error-p (vl-catch-all-apply 'gip:rm-fix-title (list (car sh) org W H)))) nil)
       (setq n (1+ n)))
     (gip:rm-sync-blocks rooms)
     (setq e (gip:rm-sync-tables sheets rooms))
     (gip:rm-report T (strcat "листов планов: " (itoa n) ", блоков номеров на листе: " (itoa (fix nn)) ", экспликаций обновлено: " (itoa (car e)) ", создано: " (itoa (cadr e)))))))
(defun gip:rm-tagged-all (/ ss i r)
  (setq r nil)
  (if (setq ss (ssget "_X" (list (list -3 (list *gip:rm-app*)))))
    (progn (setq i 0) (while (< i (sslength ss)) (setq r (cons (ssname ss i) r) i (1+ i)))))
  r)
(defun c:GIPROOMSDIST (/ r)
  (setq r (vl-catch-all-apply 'gip:rm-dist-run nil))
  (if (vl-catch-all-error-p r) (gip:rm-report nil (strcat "ошибка раскладки по листам: " (vl-catch-all-error-message r))))
  (princ))

;; ---------------------------------------------------------------- площади средствами AutoCAD (-BOUNDARY)
;; Копия подложки со стенами разбирается на отдельные линии, все слои кроме слоя стен замораживаются,
;; затем для каждого номера: -BOUNDARY по точке номера → замкнутая полилиния; её площадь и контур сохраняются.
(defun gip:rm-wall-refs (/ ss i r)
  (setq r nil)
  (if (setq ss (ssget "_X" (list '(0 . "INSERT") (list -3 (list *gip:rm-app*)))))
    (progn (setq i 0)
      (while (< i (sslength ss))
        (if (assoc 1010 (cdr (assoc *gip:rm-app* (cdr (assoc -3 (entget (ssname ss i) (list *gip:rm-app*)))))))
          (setq r (cons (ssname ss i) r)))
        (setq i (1+ i)))))
  (reverse r))
(defun gip:rm-xd (e / x l org W H)
  (setq x (cdr (assoc *gip:rm-app* (cdr (assoc -3 (entget e (list *gip:rm-app*)))))))
  (list (cdr (assoc 1010 x)) (cdr (nth 2 x)) (cdr (nth 3 x))))
(defun gip:rm-pline-pts (e / ed r)
  (setq ed (entget e) r nil)
  (foreach p ed (if (= (car p) 10) (setq r (cons (list (cadr p) (caddr p)) r))))
  (reverse r))
(defun gip:rm-make-contour (pts dx dy) (gip:rm-make-contour2 pts dx dy "C"))
(defun gip:rm-make-contour2 (pts dx dy kind)
  (entmake (append (list '(0 . "LWPOLYLINE") '(100 . "AcDbEntity") (cons 8 (gip:layer "GIP_ПОМ_КОНТУР")) '(100 . "AcDbPolyline")
                         (cons 90 (length pts)) '(70 . 1))
                   (mapcar '(lambda (p) (list 10 (+ dx (car p)) (+ dy (cadr p)))) pts)
                   (gip:rm-tag kind))))
(defun gip:rm-noplot (name)
  (vl-catch-all-apply '(lambda () (vla-put-plottable (vla-item (vla-get-layers (vla-get-activedocument (vlax-get-acad-object))) name) :vlax-false))))
(defun gip:rm-erase-layer (lay / ss i)
  (if (setq ss (ssget "_X" (list (cons 8 lay))))
    (progn (setq i 0) (while (< i (sslength ss)) (entdel (ssname ss i)) (setq i (1+ i))))))
(setq *gip:rm-st* nil)
(defun gip:rm-area-run (/ todo doc refs w0 xd org W H rooms tmp pieces lays clay e1 area nOk bad pt res osm cm l w r q o e best ba)
  (setq refs (gip:rm-wall-refs) rooms (gip:room-list) doc (vla-get-activedocument (vlax-get-acad-object)))
  (cond
    ((null refs) (gip:rm-report nil "В чертеже нет подложки помещений: сначала «Вставить на листы планов»."))
    ((null rooms) (gip:rm-report nil "Реестр помещений пуст."))
    ((null (setq todo (vl-remove-if '(lambda (r) (> (nth 2 r) 0.0)) rooms))) (gip:rm-report T "Площади уже посчитаны: контуры из панели или обведены вручную. Остальное: кнопка «Обвести помещение»."))
    (T
     (setq w0 (car refs) xd (gip:rm-xd w0) org (car xd) W (cadr xd) H (caddr xd) nOk 0 bad nil res nil lays nil
           clay (getvar "CLAYER") osm (getvar "OSMODE") cm (getvar "CMDECHO"))
     (vla-startundomark doc)
     (if (= (getvar "TILEMODE") 0) (setvar "TILEMODE" 1))
     (vl-catch-all-apply 'setvar (list "HPBOUND" 1))
     (gip:layer "GIP_ПОМ_ГРАНИЦА") (gip:layer "GIP_ПОМ_КОНТУР") (gip:layer "GIP_ПОМ_ПЕРЕМЫЧКА")
     (vl-catch-all-apply 'vla-put-freeze (list (vla-item (vla-get-layers doc) "GIP_ПОМ_ПЕРЕМЫЧКА") :vlax-false))
     (gip:rm-noplot "GIP_ПОМ_ГРАНИЦА") (gip:rm-noplot "GIP_ПОМ_КОНТУР") (gip:rm-noplot "GIP_ПОМ_ПЕРЕМЫЧКА")
     (setvar "OSMODE" 0) (setvar "CMDECHO" 0)
     ;; временная копия стен, разобранная на линии (BOUNDARY надёжно работает с обычными объектами)
     (setq tmp (vla-copy (vlax-ename->vla-object w0)))
     (setq pieces (vlax-invoke tmp 'Explode))
     (vla-delete tmp)
     (if (setq q (ssget "_X" (list '(0 . "INSERT") '(2 . "GIP_RM_J_*"))))
       (progn (setq w 0)
         (while (< w (sslength q))
           (setq e (ssname q w) w (1+ w))
           (if (< (distance (cdr (assoc 10 (entget e))) (list (car org) (cadr org) 0.0)) 1.0)
             (progn (setq tmp (vla-copy (vlax-ename->vla-object e)))
                    (setq pieces (append pieces (vlax-invoke tmp 'Explode)))
                    (vla-delete tmp))))))
     (foreach o pieces (vl-catch-all-apply 'vla-put-layer (list o "GIP_ПОМ_ГРАНИЦА")))
     (setq *gip:rm-st* (list clay osm cm pieces nil))
     (setvar "CLAYER" "GIP_ПОМ_ГРАНИЦА")
     ;; видимыми остаются только стены и перемычки: BOUNDARY анализирует то, что видно в окне
     (vlax-for l (vla-get-layers doc)
       (if (and (not (member (strcase (vla-get-name l)) '("GIP_ПОМ_ГРАНИЦА" "GIP_ПОМ_ПЕРЕМЫЧКА"))) (= (vla-get-freeze l) :vlax-false))
         (progn (setq lays (cons l lays) *gip:rm-st* (list clay osm cm pieces lays)) (vl-catch-all-apply 'vla-put-freeze (list l :vlax-true)))))
     (command "_.ZOOM" "_W" (list (- (car org) 500.0) (- (cadr org) 500.0)) (list (+ (car org) W 500.0) (+ (cadr org) H 500.0)))
     (foreach r todo
       (if (and (numberp (nth 6 r)) (numberp (nth 7 r)))
         (progn
           (setq pt (list (+ (car org) (nth 6 r)) (+ (cadr org) (nth 7 r)) 0.0) e1 (entlast))
           (command "_.-BOUNDARY" pt "")
           ;; BOUNDARY может создать и внутренние «острова» (колонны): берём самый большой из новых объектов
           (setq best nil ba 0.0 e (if e1 (entnext e1) (entnext)))
           (while e
             (if (member (cdr (assoc 0 (entget e))) '("LWPOLYLINE" "POLYLINE"))
               (if (> (setq area (vla-get-area (vlax-ename->vla-object e))) ba) (setq ba area best e)))
             (setq e (entnext e)))
           (if best
             (progn
               (setq res (cons (list (car r) (gip:rm-r2 (/ ba 1000000.0)) (gip:rm-pline-pts best)) res))
               (gip:rm-perim-put (car r) (gip:rm-pts-perim (gip:rm-pline-pts best)))
               (setq nOk (1+ nOk))
               (setq e (if e1 (entnext e1) (entnext)))
               (while e (setq q (entnext e)) (entdel e) (setq e q)))
             (setq bad (cons (car r) bad))))))
     (foreach l lays (vl-catch-all-apply 'vla-put-freeze (list l :vlax-false)))
     (foreach o pieces (vl-catch-all-apply 'vla-delete (list o)))
     (setvar "CLAYER" clay) (setvar "OSMODE" osm) (setvar "CMDECHO" cm)
     (command "_.ZOOM" "_P")
     (vla-endundomark doc)
     ;; площади -> реестр; контуры (скрытый слой, не печатается) на каждом листе
     (setq rooms (mapcar '(lambda (r / q)
                            (if (setq q (assoc (car r) res))
                              (list (nth 0 r) (nth 1 r) (cadr q) (nth 3 r) (nth 4 r) (gip:rm-vol (cadr q) (nth 4 r)) (nth 6 r) (nth 7 r))
                              r))
                         rooms))
     (gip:room-put rooms)
     (foreach r res
       (foreach w refs
         (setq xd (gip:rm-xd w))
         (gip:rm-make-contour (caddr r) (- (car (car xd)) (car org)) (- (cadr (car xd)) (cadr org)))))
     (gip:rm-sync-blocks rooms)
     (gip:rm-sync-tables (gip:rm-sheets) rooms)
     (gip:rm-report (null bad)
       (strcat "площади посчитаны: " (itoa nOk) " из " (itoa (length rooms))
               (if bad (strcat ". Не удалось замкнуть контур у помещений: " (gip:rm-join (reverse bad)) ". Нарисуйте перемычки в проёмах линиями на слое GIP_ПОМ_ПЕРЕМЫЧКА и повторите.") "")))))
  (princ))

(defun c:GIPROOMSAREA (/ r l)
  (setq r (vl-catch-all-apply 'gip:rm-area-run nil))
  (if (vl-catch-all-error-p r)
    (progn
      (if *gip:rm-st*
        (progn
          (foreach l (nth 4 *gip:rm-st*) (vl-catch-all-apply 'vla-put-freeze (list l :vlax-false)))
          (foreach l (nth 3 *gip:rm-st*) (vl-catch-all-apply 'vla-delete (list l)))
          (vl-catch-all-apply 'setvar (list "CLAYER" (nth 0 *gip:rm-st*)))
          (vl-catch-all-apply 'setvar (list "OSMODE" (nth 1 *gip:rm-st*)))
          (vl-catch-all-apply 'setvar (list "CMDECHO" (nth 2 *gip:rm-st*)))
          (setq *gip:rm-st* nil)))
      (gip:rm-report nil (strcat "ошибка расчёта площадей: " (vl-catch-all-error-message r)))))
  (princ))

;; ---------------------------------------------------------------- ручной контур помещения
;; выбрать номер помещения, затем обвести полилинией (с привязками) или указать готовую замкнутую; площадь -> реестр
(defun gip:rm-trace-run (/ sel e no r p pe e1 obj area cm osm rooms ed)
  (setq rooms (gip:room-list))
  (if (null rooms)
    (gip:rm-report nil "Реестр помещений пуст.")
    (progn
      (setq sel (entsel "\nГИП: выберите номер помещения (кружок с цифрой): "))
      (setq e (if sel (car sel)))
      (cond
        ((or (null e) (/= (cdr (assoc 0 (entget e))) "INSERT") (not (member e (gip:rm-num-refs))))
         (gip:rm-report nil "Не выбран блок номера помещения."))
        (T
         (setq no (gip:rm-num (vlax-ename->vla-object e)) r (assoc no rooms))
         (initget "Pick")
         (setq p (getpoint (strcat "\nПомещение " (itoa no) ": первый угол контура или [Pick - выбрать готовую полилинию]: ")))
         (setq cm (getvar "CMDECHO") osm (getvar "OSMODE"))
         (cond
           ((= p "Pick") (setq sel (entsel "\nВыберите замкнутую полилинию помещения: ") pe (if sel (car sel))))
           ((and p (listp p))
            (setq e1 (entlast))
            (command "_.PLINE" p)
            (while (> (getvar "CMDACTIVE") 0) (command pause))
            (setq pe (entlast))
            (if (equal pe e1) (setq pe nil))))
         (setvar "CMDECHO" cm)
         (cond
           ((or (null pe) (null r) (not (member (cdr (assoc 0 (entget pe))) '("LWPOLYLINE"))))
            (gip:rm-report nil "Контур не получен (нужна полилиния)."))
           (T
            (setq obj (vlax-ename->vla-object pe))
            (vla-put-closed obj :vlax-true)
            (setq area (gip:rm-r2 (/ (vla-get-area obj) 1000000.0)))
            (gip:rm-perim-put no (/ (vlax-curve-getdistatparam pe (vlax-curve-getendparam pe)) 1000.0))
            (vla-put-layer obj (gip:layer "GIP_ПОМ_КОНТУР"))
            (gip:rm-noplot "GIP_ПОМ_КОНТУР")
            (gip:rm-tag-obj obj "C")
            (setq rooms (subst (list (nth 0 r) (nth 1 r) area (nth 3 r) (nth 4 r) (gip:rm-vol area (nth 4 r)) (nth 6 r) (nth 7 r)) r rooms))
            (gip:room-put rooms)
            (gip:rm-sync-blocks rooms)
            (gip:rm-report T (strcat "помещение " (itoa no) ": площадь " (rtos area 2 1) " кв.м"
                                     (if (> (nth 3 r) 0.0) (strcat " (у дизайнера " (rtos (nth 3 r) 2 1) ")") ""))))))))))
(defun c:GIPROOMSTRACE (/ r)
  (setq r (vl-catch-all-apply 'gip:rm-trace-run nil))
  (if (vl-catch-all-error-p r) (gip:rm-report nil (strcat "ошибка обводки: " (vl-catch-all-error-message r))))
  (princ))
(defun gip:rm-join (l / s)
  (setq s "")
  (foreach x l (setq s (strcat s (if (= s "") "" ", ") (itoa x))))
  s)

;; ---------------------------------------------------------------- команды панели
(defun c:GIPROOMSIMPORT ()
  (vl-file-delete (strcat (getvar "TEMPPREFIX") "gip_rooms_out.txt"))
  (gip:rm-import (strcat (getvar "TEMPPREFIX") *gip:rm-file*))
  (princ))
(defun c:GIPROOMSYNC (/ rooms n t2)
  (setq rooms (gip:room-list))
  (if (null rooms)
    (gip:rm-report nil "Реестр помещений пуст.")
    (progn
      (setq n (gip:rm-sync-blocks rooms))
      (setq t2 (gip:rm-sync-tables (gip:rm-sheets) rooms))
      (gip:rm-report T (strcat "блоков номеров обновлено: " (itoa n) ", экспликаций обновлено: " (itoa (car t2)) ", создано: " (itoa (cadr t2))))))
  (princ))
;; блоки -> реестр (если название/высоту поправили атрибутами блока), затем отправить реестр панели
(defun c:GIPROOMSREAD (/ rooms e obj no r nm h out)
  (setq rooms (gip:rm-read-area-table (gip:room-list)) out nil)
  (foreach e (gip:rm-num-refs)
    (setq obj (vlax-ename->vla-object e) no (gip:rm-num obj))
    (if (and (> no 0) (not (assoc no out)))
      (progn
        (setq r (assoc no rooms)
              nm (gip:rm-att-val obj "NAME") h (atof (gip:rm-att-val obj "H")))
        (setq out (cons (list no (if (/= nm "") nm (if r (cadr r) ""))
                              (if r (nth 2 r) 0.0) (if r (nth 3 r) 0.0) (if (> h 0) h (if r (nth 4 r) 0.0))
                              (gip:rm-vol (if r (nth 2 r) 0.0) (if (> h 0) h (if r (nth 4 r) 0.0)))
                              (if r (nth 6 r)) (if r (nth 7 r))) out)))))
  (if out (gip:room-put (vl-sort out '(lambda (a b) (< (car a) (car b))))))
  (gip:rm-write-reg)
  (princ))

;; ---------------------------------------------------------------- помещения без PDF (свой план)
;; щелчок в помещении -> номер, название, высота -> блок номера и строка реестра; затем по желанию обвести контур
;; (полилиния по углам или готовая) — площадь, периметр. Enter на запросе точки — закончить.
(defun gip:rm-add-run (/ rooms p no nm h obj r e1 pe area n0 cnt ed pts per i a b)
  (regapp *gip:rm-app*)
  (setq cnt 0)
  (while (setq p (getpoint "\nГИП: точка номера помещения (внутри комнаты; Enter — закончить): "))
    (setq rooms (gip:room-list) n0 (1+ (apply 'max (cons 0 (mapcar 'car rooms)))))
    (setq no (getint (strcat "\nНомер помещения <" (itoa n0) ">: ")))
    (if (null no) (setq no n0))
    (setq nm (getstring T "\nНазвание помещения: "))
    (setq h (getreal "\nВысота потолка, мм <2700>: "))
    (if (null h) (setq h 2700.0))
    (setq r (list no nm 0.0 0.0 h 0.0 nil nil))
    (setq rooms (vl-sort (cons r (vl-remove (assoc no rooms) rooms)) '(lambda (a b) (< (car a) (car b)))))
    (setq obj (gip:rm-insert (gip:rm-ensure-block) (car p) (cadr p) "GIP_Номера помещений" "SN"))
    (gip:rm-fill-marker obj r)
    ;; контур
    (initget "Pick")
    (setq pe nil e1 (entlast)
          p (getpoint (strcat "\nПомещение " (itoa no) ": первый угол контура, [Pick - готовая полилиния] или Enter — без контура: ")))
    (cond
      ((= p "Pick") (setq p (entsel "\nВыберите замкнутую полилинию помещения: ") pe (if p (car p))))
      ((and p (listp p))
       (command "_.PLINE" p)
       (while (> (getvar "CMDACTIVE") 0) (command pause))
       (setq pe (entlast))
       (if (equal pe e1) (setq pe nil))))
    (if (and pe (= (cdr (assoc 0 (entget pe))) "LWPOLYLINE"))
      (progn
        ;; замкнуть, на слой контуров; площадь и периметр по вершинам (контур из отрезков)
        (setq ed (entget pe) ed (subst (cons 70 (logior 1 (cdr (assoc 70 ed)))) (assoc 70 ed) ed)
              ed (subst (cons 8 (gip:layer "GIP_ПОМ_КОНТУР")) (assoc 8 ed) ed))
        (entmod ed)
        (setq pts (mapcar 'cdr (vl-remove-if-not '(lambda (x) (= (car x) 10)) ed)) area 0.0 per 0.0 i 0)
        (while (< i (length pts))
          (setq a (nth i pts) b (nth (rem (1+ i) (length pts)) pts)
                area (+ area (- (* (car a) (cadr b)) (* (car b) (cadr a)))) per (+ per (distance a b)) i (1+ i)))
        (setq area (gip:rm-r2 (/ (abs area) 2000000.0)))
        (gip:rm-perim-put no (/ per 1000.0))
        (gip:rm-noplot "GIP_ПОМ_КОНТУР")
        (gip:rm-tag-obj (vlax-ename->vla-object pe) "C")
        (setq r (list no nm area 0.0 h (gip:rm-vol area h) nil nil)
              rooms (subst r (assoc no rooms) rooms))))
    (gip:room-put rooms)
    (gip:rm-sync-blocks rooms)
    (setq cnt (1+ cnt))
    (princ (strcat "\nГИП: помещение " (itoa no) " «" nm "»" (if (> (nth 2 r) 0.0) (strcat ", " (rtos (nth 2 r) 2 1) " кв.м") ", площадь — обведите позже кнопкой «Обвести помещение»"))))
  (gip:rm-report T (strcat "добавлено помещений: " (itoa cnt) ".")))
(defun c:GIPROOMADD (/ r)
  (setq r (vl-catch-all-apply 'gip:rm-add-run nil))
  (if (vl-catch-all-error-p r) (gip:rm-report nil (strcat "ошибка: " (vl-catch-all-error-message r))))
  (gip:rm-write-reg)
  (princ))
