;;; ============================================================================
;;; Монтажная схема: аппараты — блоки GIPM_* на DIN-рейках, провода, гребёнки,
;;; шины N и PE, бирки. Единицы расчёта — пункты трафаретов Visio (1 модуль = 50,2 pt),
;;; затем масштаб под лист А3.
;;; ============================================================================
(setq *gip:MW* 50.2 *gip:GH* 224.0 *gip:LANE* 9.0 *gip:RC* 9.0)
(setq *gip:netc* '(("L" . 15213083) ("L1" . 9128476) ("L2" . 1287480) ("L3" . 15213083) ("N" . 2060241) ("CTL" . 16088064)))

;; клеммы трафаретов (x уже в масштабе ширины блока, y от верха корпуса)
(setq *gip:st-term* '(
  ("dk_a1" 223.9 (("L" 25.1 20.0)) (("L" 25.1 204.0)))
  ("dk_a2" 223.9 (("L" 25.1 20.0) ("N" 75.3 20.0)) (("L" 25.1 204.0) ("N" 75.3 204.0)))
  ("dk_a3" 223.9 (("L1" 25.1 20.0) ("L2" 75.3 20.0) ("L3" 125.5 20.0)) (("L1" 25.1 204.0) ("L2" 75.3 204.0) ("L3" 125.5 204.0)))
  ("dk_a4" 223.9 (("L1" 25.1 20.0) ("L2" 75.3 20.0) ("L3" 125.5 20.0) ("N" 175.7 20.0)) (("L1" 25.1 204.0) ("L2" 75.3 204.0) ("L3" 125.5 204.0) ("N" 175.7 204.0)))
  ("dk_dif" 232.4 (("N" 25.1 20.0) ("L" 75.6 20.0)) (("N" 25.1 212.4) ("L" 75.6 212.4)))
  ("dk_dif4" 232.4 (("N" 25.1 20.0) ("L1" 76.0 20.0) ("L2" 127.0 20.0) ("L3" 177.5 20.0)) (("N" 25.1 212.5) ("L1" 76.0 212.5) ("L2" 127.0 212.5) ("L3" 177.5 212.5)))
  ("dk_rcd2" 223.9 (("L" 25.0 19.5) ("N" 76.0 19.5)) (("L" 25.0 204.4) ("N" 76.0 204.4)))
  ("dk_rcd4" 223.9 (("L1" 25.1 19.5) ("L2" 76.2 19.5) ("L3" 127.2 19.5) ("N" 178.6 19.5)) (("L1" 25.1 204.5) ("L2" 76.2 204.5) ("L3" 127.2 204.5) ("N" 178.6 204.5)))
  ("abb_km2" 249.4 (("L" 14.7 21.5) ("A1" 25.0 44.0)) (("L" 14.7 228.0) ("A2" 25.0 205.3)))
  ("abb_km4" 249.4 (("L1" 15.0 37.4) ("L2" 36.3 37.4) ("L3" 66.2 37.4) ("A1" 51.2 23.6)) (("L1" 15.0 212.0) ("L2" 36.3 212.0) ("L3" 66.2 212.0) ("A2" 51.2 225.9)))
  ("ab_a1" 249.4 (("L" 24.8 23.4)) (("L" 24.8 226.3)))
  ("ab_a2" 249.4 (("L" 24.8 23.4) ("N" 74.4 23.4)) (("L" 24.8 226.3) ("N" 74.4 226.3)))
  ("ab_a3" 249.4 (("L1" 24.8 23.4) ("L2" 74.4 23.4) ("L3" 124.0 23.4)) (("L1" 24.8 226.3) ("L2" 74.4 226.3) ("L3" 124.0 226.3)))
  ("ab_a4" 249.4 (("L1" 24.8 23.4) ("L2" 74.4 23.4) ("L3" 124.0 23.4) ("N" 173.6 23.4)) (("L1" 24.8 226.3) ("L2" 74.4 226.3) ("L3" 124.0 226.3) ("N" 173.6 226.3)))
  ("ab_dif" 249.4 (("L" 24.8 23.4) ("N" 74.4 23.4)) (("L" 24.8 226.3) ("N" 74.4 226.3)))
  ("ab_rcd2" 249.4 (("L" 24.8 23.4) ("N" 74.4 23.4)) (("L" 24.8 226.3) ("N" 74.4 226.3)))
  ("ab_fire2" 249.4 (("L" 24.8 23.4) ("N" 74.4 23.4)) (("L" 24.8 226.3) ("N" 74.4 226.3)))
  ("ab_rcd4" 249.4 (("L1" 24.8 23.4) ("L2" 74.4 23.4) ("L3" 124.0 23.4) ("N" 173.6 23.4)) (("L1" 24.8 226.3) ("L2" 74.4 226.3) ("L3" 124.0 226.3) ("N" 173.6 226.3)))
  ("ab_fire4" 249.4 (("L1" 24.8 23.4) ("L2" 74.4 23.4) ("L3" 124.0 23.4) ("N" 173.6 23.4)) (("L1" 24.8 226.3) ("L2" 74.4 226.3) ("L3" 124.0 226.3) ("N" 173.6 226.3)))
  ("ab_dif4" 249.4 (("L1" 24.9 23.4) ("L2" 74.8 23.4) ("L3" 124.8 23.4) ("N" 174.6 23.4)) (("L1" 24.9 226.3) ("L2" 74.8 226.3) ("L3" 124.8 226.3) ("N" 174.6 226.3)))
  ("ch_a1" 226.8 (("L" 25.5 17.0)) (("L" 25.5 209.6)))
  ("ch_a2" 226.8 (("L" 25.5 17.0) ("N" 76.5 17.0)) (("L" 25.5 209.6) ("N" 76.5 209.6)))
  ("ch_a3" 226.8 (("L1" 25.5 17.0) ("L2" 76.5 17.0) ("L3" 127.6 17.0)) (("L1" 25.5 209.6) ("L2" 76.5 209.6) ("L3" 127.6 209.6)))
  ("ch_a4" 226.8 (("L1" 25.5 17.0) ("L2" 76.5 17.0) ("L3" 127.6 17.0) ("N" 178.6 17.0)) (("L1" 25.5 209.6) ("L2" 76.5 209.6) ("L3" 127.6 209.6) ("N" 178.6 209.6)))
  ("ch_rcd2" 226.8 (("N" 25.5 17.0) ("L" 76.5 17.0)) (("N" 25.5 209.6) ("L" 76.5 209.6)))
  ("ch_rcd4" 226.8 (("N" 25.5 17.0) ("L1" 76.5 17.0) ("L2" 127.6 17.0) ("L3" 178.6 17.0)) (("N" 25.5 209.6) ("L1" 76.5 209.6) ("L2" 127.6 209.6) ("L3" 178.6 209.6)))
  ("rel_vip" 240.9 (("L" 25.5 21.6) ("N" 76.5 21.6)) (("Lo" 25.5 218.8)))))
;; ширина трафарета в пунктах (для пересчёта клемм на ширину аппарата)
(setq *gip:st-vbw* '(("dk_a1" . 50.2) ("dk_a2" . 100.3) ("dk_a3" . 150.5) ("dk_a4" . 200.7) ("dk_dif" . 101.5) ("dk_dif4" . 203.0)
  ("dk_rcd2" . 102.0) ("dk_rcd4" . 204.1) ("abb_km2" . 50.5) ("abb_km4" . 102.0) ("ab_a1" . 49.6) ("ab_a2" . 99.2) ("ab_a3" . 148.8)
  ("ab_a4" . 198.4) ("ab_dif" . 99.2) ("ab_dif4" . 199.6) ("ab_rcd2" . 99.2) ("ab_rcd4" . 198.4) ("ab_fire2" . 99.2) ("ab_fire4" . 198.4)
  ("ch_a1" . 51.0) ("ch_a2" . 102.0) ("ch_a3" . 153.1) ("ch_a4" . 204.1) ("ch_rcd2" . 102.0) ("ch_rcd4" . 204.1) ("rel_vip" . 102.0)))

(defun gip:stencil (d s is3 / k P n)
  (setq k (gip:g d "kind"))
  (cond
    ((= k "km") (if (> (gip:g d "w") 1) "abb_km4" "abb_km2"))
    ((= k "rn") "rel_vip")
    ((member (gip:g s "brand") '("abb" "chint"))
     (setq P (if (= (gip:g s "brand") "abb") "ab_" "ch_"))
     (setq n (cond ((= k "in") (if is3 (if (= (length (gip:g d "poles")) 4) "a4" "a3") "a2"))
                   ((= k "a1") "a1") ((= k "a3") "a3") ((= k "dif") "dif") ((= k "dif4") "dif4") ((= k "rcd") (if (= (gip:g d "w") 4) "rcd4" "rcd2"))
                   ((= k "fire") (if (= P "ab_") (if is3 "fire4" "fire2") (if is3 "rcd4" "rcd2")))
                   (T nil)))
     (if (and n (assoc (strcat P n) *gip:st-term*)) (strcat P n) nil))
    ((= (gip:g s "brand") "dekraft")
     (cond ((= k "in") (if is3 (if (= (length (gip:g d "poles")) 4) "dk_a4" "dk_a3") "dk_a2"))
           ((= k "a1") "dk_a1") ((= k "a3") "dk_a3") ((= k "dif") "dk_dif") ((= k "dif4") "dk_dif4")
           ((= k "rcd") (if (= (gip:g d "w") 4) "dk_rcd4" "dk_rcd2")) ((= k "fire") (if is3 "dk_rcd4" "dk_rcd2")) (T nil)))
    (T nil)))

;; имя блока аппарата на монтажной схеме
(defun gip:mblock (d s is3 / st k)
  (setq st (gip:g d "st") k (gip:g d "kind"))
  (cond (st (strcat "GIPM_" st))
        ((= k "xb") (strcat "GIPM_G_xb_" (itoa (gip:g d "w"))))
        ((and (= k "in") (= (gip:g d "inType") "qs")) (strcat "GIPM_G_qs_" (itoa (gip:g d "w"))))
        ((member (gip:g s "brand") '("iek" "chint" "abb" "dekraft"))
         (strcat "GIPM_G_" (gip:g s "brand") "_" (if (and (= k "rcd") (= (gip:g d "w") 4)) "fire" k) "_" (itoa (gip:g d "w"))))
        (T (strcat "GIPM_G_iek_" k "_" (itoa (gip:g d "w"))))))

(defun gip:rating (d) (if (or (member (gip:g d "kind") '("rcd" "fire")) (and (= (gip:g d "kind") "in") (= (gip:g d "inType") "qs"))) (strcat (itoa (gip:g d "In")) "A") (strcat "C" (itoa (gip:g d "In")))))

;; клемма аппарата относительно левого верхнего угла
(defun gip:term (d side pole / st tr lst t1 kx arr i)
  (setq st (gip:g d "st"))
  (if (and st (setq tr (cdr (assoc st *gip:st-term*))))
    (progn
      (setq lst (if (= side "top") (cadr tr) (caddr tr)))
      (setq t1 (cdr (assoc pole lst)))
      (if (null t1) (setq t1 (cdr (car lst))))
      (setq kx (/ (* (gip:g d "w") *gip:MW*) (cdr (assoc st *gip:st-vbw*))))
      (list (* (car t1) kx) (cadr t1)))
    (progn
      (setq arr (if (= side "top") (gip:g d "poles") (gip:g d "bot")))
      (setq i (gip:index pole arr)) (if (null i) (setq i 0))
      (list (/ (* (+ i 0.5) (gip:g d "w") *gip:MW*) (max 1 (length arr))) (if (= side "top") 22.0 (- *gip:GH* 22.0))))))

(defun gip:net (d pole is3)
  (cond ((member pole '("N" "A2")) "N") ((= pole "A1") "CTL")
        ((member pole '("L" "Lo")) (if is3 (gip:gn d "phase" "L1") "L")) (T pole)))
;; гребёнка: тип по аппарату (1P, 2P — однополюсные с N, 3P, 4P); фазы однополюсных проверяются при сборке участка
(defun gip:comb-key (d / k)
  (setq k (gip:g d "kind"))
  (cond ((= k "a1") "1P") ((= k "dif") "2P") ((= k "a3") "3P") ((= k "dif4") "4P") (T nil)))
(defun gip:ph-next (p) (cdr (assoc p '(("L1" . "L2") ("L2" . "L3") ("L3" . "L1")))))
;; можно ли продолжить участок гребёнки аппаратом d: одна фаза подряд (однофазная гребёнка)
;; или L1 → L2 → L3 → L1 (трёхфазная гребёнка)
(defun gip:comb-join (run d / dl p q mode)
  (setq dl (last (gip:g run "devs")) p (gip:gn dl "phase" "L") q (gip:gn d "phase" "L") mode (gip:g run "mode"))
  (cond ((not (member (gip:g run "key") '("1P" "2P"))) "fix")
        ((and (/= mode "cyc") (= p q)) "same")
        ((and (/= mode "same") (= (gip:ph-next p) q)) "cyc")
        (T nil)))

;; ---------------------------------------------------------------- преобразование координат pt -> модель
(defun gip:X (x) (+ (car *gip:mo*) (* x (caddr *gip:mo*))))
(defun gip:Y (y) (- (cadr *gip:mo*) (* y (caddr *gip:mo*))))
(defun gip:K (v) (* v (caddr *gip:mo*)))

;; ---------------------------------------------------------------- примитивы монтажной схемы
(setq *gip:mlay* "GIP_Монтаж")
(defun gip:aci (tc / r g b)
  (setq r (/ tc 65536) g (rem (/ tc 256) 256) b (rem tc 256))
  (cond ((and (> r 235) (> g 235) (> b 235)) 7)
        ((< (+ r g b) 90) 7)
        ((and (> r 200) (> g 200) (< b 80)) 2)
        ((and (> r 180) (< g 90) (< b 90)) 1)
        ((and (> r 200) (> g 100) (< g 180) (< b 60)) 30)
        ((and (< r 80) (> g 120) (< b 100)) 3)
        ((and (< r 80) (> b 150)) 5)
        ((and (> r 100) (< r 160) (< g 90) (< b 60)) 34)
        ((> (+ r g b) 600) 9)
        ((> (+ r g b) 400) 8)
        (T 8)))
(defun gip:ent-head (typ tc / l)
  (setq l (list (cons 0 typ) '(100 . "AcDbEntity") (cons 8 *gip:mlay*)))
  (if tc (setq l (append l (list (cons 62 (gip:aci tc)) (cons 420 tc)))))
  l)

;; полилиния по точкам pt (список (x y)), bulges — список той же длины или nil
(defun gip:mpoly (pts closed tc w bul / l i)
  (setq l (append (gip:ent-head "LWPOLYLINE" tc)
                  (list '(100 . "AcDbPolyline") (cons 90 (length pts)) (cons 70 (if closed 1 0)) (cons 43 (gip:K w)))))
  (setq i 0)
  (foreach p pts
    (setq l (append l (list (list 10 (gip:X (car p)) (gip:Y (cadr p))))))
    (if (and bul (/= (nth i bul) 0.0)) (setq l (append l (list (cons 42 (nth i bul))))))
    (setq i (1+ i)))
  (gip:mk l *gip:tag*))

;; заливка: полный набор кодов, как у штриховок из файлов ГИП (их AutoCAD создаёт), иначе — через ActiveX
(defun gip:mhatch (pts tc / l e)
  (setq l (append (gip:ent-head "HATCH" tc)
                  (list '(100 . "AcDbHatch") '(10 0.0 0.0 0.0) '(210 0.0 0.0 1.0) '(2 . "SOLID") '(70 . 1) '(71 . 0) '(91 . 1)
                        '(92 . 7) '(72 . 1) '(73 . 1) (cons 93 (length pts)))))
  (foreach p pts (setq l (append l (list (list 10 (gip:X (car p)) (gip:Y (cadr p)) 0.0) '(42 . 0.0)))))
  (setq l (append l (list '(97 . 0) '(75 . 0) '(76 . 1) '(47 . 1.0) '(98 . 1) (list 10 (gip:X (car (car pts))) (gip:Y (cadr (car pts))) 0.0)
                          '(450 . 0) '(451 . 0) '(460 . 0.0) '(461 . 0.0) '(452 . 0) '(462 . 0.0) '(453 . 0) '(470 . ""))))
  (setq e (entmakex (append l (gip:tag-list *gip:tag*))))
  (if (null e) (setq e (gip:mhatch-ax pts tc)))
  e)
(defun gip:mhatch-ax (pts tc / l pl o h arr r e)
  (setq l (list '(0 . "LWPOLYLINE") '(100 . "AcDbEntity") (cons 8 *gip:mlay*) '(100 . "AcDbPolyline") (cons 90 (length pts)) '(70 . 1)))
  (foreach p pts (setq l (append l (list (list 10 (gip:X (car p)) (gip:Y (cadr p)))))))
  (if (setq pl (entmakex l))
    (progn
      (setq o (vlax-ename->vla-object pl))
      (setq h (vl-catch-all-apply 'vla-addhatch (list (gip:ms) 1 "SOLID" :vlax-false)))
      (if (not (vl-catch-all-error-p h))
        (progn
          (setq arr (vlax-make-safearray vlax-vbObject '(0 . 0)))
          (vlax-safearray-fill arr (list o))
          (setq r (vl-catch-all-apply 'vla-appendouterloop (list h (vlax-make-variant arr))))
          (if (vl-catch-all-error-p r)
            (progn (vla-delete h) (setq h nil))
            (progn
              (vl-catch-all-apply 'vla-evaluate (list h))
              (vla-put-layer h *gip:mlay*)
              (vla-put-color h (gip:aci tc))
              (setq e (vlax-vla-object->ename h))
              (entmod (append (entget e) (gip:tag-list *gip:tag*))))))
        (setq h nil))
      (entdel pl)))
  e)

(defun gip:rectpts (x y w h) (list (list x y) (list (+ x w) y) (list (+ x w) (+ y h)) (list x (+ y h))))
;; прямоугольник: заливка fill (или nil) и контур stroke (или nil)
(defun gip:mrect (x y w h fill stroke)
  (if fill (gip:mhatch (gip:rectpts x y w h) fill))
  (if stroke (gip:mpoly (gip:rectpts x y w h) T stroke 0.0 nil)))
;; скруглённый прямоугольник (контур)
(defun gip:mrrect (x y w h r stroke / b)
  (setq b (- (/ (sin (/ pi 8)) (cos (/ pi 8)))))
  (gip:mpoly (list (list (+ x r) y) (list (- (+ x w) r) y) (list (+ x w) (+ y r)) (list (+ x w) (- (+ y h) r))
                   (list (- (+ x w) r) (+ y h)) (list (+ x r) (+ y h)) (list x (- (+ y h) r)) (list x (+ y r)))
             T stroke 0.0 (list 0.0 b 0.0 b 0.0 b 0.0 b)))
(defun gip:mcircle (x y r tc)
  (gip:mk (append (gip:ent-head "CIRCLE" tc) (list '(100 . "AcDbCircle") (list 10 (gip:X x) (gip:Y y) 0.0) (cons 40 (gip:K r)))) *gip:tag*))
(defun gip:mdisk (x y r tc / pts i a)
  (setq pts nil i 0)
  (while (< i 16) (setq a (/ (* i 2 pi) 16) pts (append pts (list (list (+ x (* r (cos a))) (+ y (* r (sin a)))))) i (1+ i)))
  (gip:mhatch pts tc))
(defun gip:mtext (x y fs txt tc ha / h)
  (setq h (gip:K (* fs 0.72)))
  (gip:mk (append (gip:ent-head "TEXT" tc)
                  (list '(100 . "AcDbText") (list 10 (gip:X x) (gip:Y y) 0.0) (cons 40 h) (cons 1 txt) '(7 . "Standard")
                        (cons 72 ha) (list 11 (gip:X x) (gip:Y y) 0.0) '(100 . "AcDbText")))
          *gip:tag*))
(defun gip:mline (x1 y1 x2 y2 tc w) (gip:mpoly (list (list x1 y1) (list x2 y2)) nil tc w nil))

;; провод со скруглёнными углами (дуги-сопряжения через bulge)
(defun gip:mwire (pts net / out bul i p0 p1 p2 l1 l2 r a b d1x d1y d2x d2y cr dt th)
  (setq out (list (car pts)) bul (list 0.0) i 1)
  (while (< i (1- (length pts)))
    (setq p0 (nth (1- i) pts) p1 (nth i pts) p2 (nth (1+ i) pts))
    (setq l1 (distance p0 p1) l2 (distance p1 p2))
    (setq r (min *gip:RC* (/ l1 2.0) (/ l2 2.0)))
    (if (< r 0.5)
      (setq out (append out (list p1)) bul (append bul (list 0.0)))
      (progn
        (setq a (list (+ (car p1) (/ (* (- (car p0) (car p1)) r) l1)) (+ (cadr p1) (/ (* (- (cadr p0) (cadr p1)) r) l1))))
        (setq b (list (+ (car p1) (/ (* (- (car p2) (car p1)) r) l2)) (+ (cadr p1) (/ (* (- (cadr p2) (cadr p1)) r) l2))))
        ;; направление в координатах модели (ось Y вверх): y_модели = -y_pt
        (setq d1x (- (car p1) (car p0)) d1y (- (- (cadr p1) (cadr p0))) d2x (- (car p2) (car p1)) d2y (- (- (cadr p2) (cadr p1))))
        (setq cr (- (* d1x d2y) (* d1y d2x)) dt (+ (* d1x d2x) (* d1y d2y)))
        (setq th (atan (abs cr) dt))
        (setq out (append out (list a b)) bul (append bul (list (* (if (minusp cr) -1.0 1.0) (/ (sin (/ th 4)) (cos (/ th 4)))) 0.0)))))
    (setq i (1+ i)))
  (setq out (append out (list (last pts))) bul (append bul (list 0.0)))
  ;; bulge относится к вершине, с которой начинается дуга
  (gip:mpoly out nil (cdr (assoc net *gip:netc*)) 3.6 (gip:bul-shift bul)))
(defun gip:bul-shift (bul / r i)
  ;; bul: 0 у начала, для каждого скругления — (bulge 0) у точек a b; дуга идёт от a к b => bulge ставим на a
  (setq r nil i 0)
  (foreach v bul (setq r (append r (list v))))
  r)
(defun gip:ferr (x y net up / tc)
  (setq tc (cdr (assoc net *gip:netc*)))
  (gip:mrect (- x 4) (if up (- y 15) (+ y 3)) 8.0 12.0 tc 2236962))

;; бирка: жёлтый прямоугольник с текстом
(defun gip:split-text (s mx ml / words out cur)
  (setq out nil cur "")
  (foreach w (gip:split s " ")
    (if (<= (strlen (gip:trim (strcat cur " " w))) mx)
      (setq cur (gip:trim (strcat cur " " w)))
      (progn (if (/= cur "") (setq out (append out (list cur))))
             (while (> (strlen w) mx) (setq out (append out (list (strcat (substr w 1 (1- mx)) "-"))) w (substr w mx)))
             (setq cur w))))
  (if (/= cur "") (setq out (append out (list cur))))
  (if (> (length out) ml) (setq out (append (gip:take out (1- ml)) (list (strcat (substr (nth (1- ml) out) 1 (max 1 (1- mx))) "…")))))
  out)
(defun gip:tagbox (x y txt w / lines h i)
  (setq lines (gip:split-text txt (fix (/ (- w 6) 5.6)) 2) h (+ 4 (* (length lines) 11)))
  (gip:mrect x y w h 16776960 8026624)
  (setq i 0)
  (foreach ln lines (gip:mtext (+ x (/ w 2.0)) (+ y 11 (* i 11)) 9.6 ln 1118481 1) (setq i (1+ i))))
(defun gip:loadtag (x y w h d / name per lines i)
  (setq name (gip:g d "name"))
  (if (gip:starts name "Освещение: ") (setq name (strcat "Освещ. " (substr name 12))))
  (setq per (max 5 (fix (/ (- w 4) 4.6))) lines (gip:split-text name per 4))
  (gip:mrect x y w (+ 10 (* (length lines) 9.5)) 16776960 8026624)
  (gip:mtext (+ x (/ w 2.0)) (+ y 9) 8.4 (gip:gn d "ref" "") 1194109 1)
  (setq i 0)
  (foreach ln lines (gip:mtext (+ x (/ w 2.0)) (+ y 18.5 (* i 9.5)) 8.2 ln 1118481 1) (setq i (1+ i))))
(defun gip:facetag (x y w d / n ww)
  (setq n (cond ((= (gip:g d "id") "c2") "Защита катушки KM1")
                ((and (= (gip:g d "kind") "in") (= (gip:g d "inType") "qs")) "Вводной рубильник") ((= (gip:g d "kind") "in") "Вводной автомат") ((= (gip:g d "kind") "rn") "Реле напряжения")
                ((= (gip:g d "kind") "fire") "УЗО противопожарное") ((= (gip:g d "kind") "km") "Контактор")
                ((= (gip:g d "kind") "rcd") (strcat "УЗО гр. " (itoa (gip:gn d "rcdNo" 0)))) (T nil)))
  (cond ((= (gip:g d "kind") "xb") (gip:tagbox (+ x 4) (+ y (* (gip:g d "h") 0.32)) (strcat (gip:gn d "ref" "") " Кросс-модуль") (- w 8)))
        (n (setq ww (max (- w 4) 44.0)) (gip:tagbox (+ x (/ (- w ww) 2.0)) y (strcat (gip:gn d "ref" "") " " n) ww))))
(defun gip:busshape (x y n col dark / w i cx)
  (setq w (+ (* n 13) 22))
  (gip:mpoly (list (list (+ x 4) (+ y 14)) (list (+ x 10) (- y 2)) (list (- (+ x w) 10) (- y 2)) (list (- (+ x w) 4) (+ y 14))) T 9079434 0.0 nil)
  (gip:mrect x (+ y 14) w 9.0 col dark)
  (setq i 0)
  (while (< i n)
    (setq cx (+ x 15 (* i 13)))
    (gip:mdisk cx (+ y 8) 5.0 14277081) (gip:mcircle cx (+ y 8) 5.0 5592405)
    (gip:mline (- cx 3) (+ y 5) (+ cx 3) (+ y 11) 7829367 0.0) (gip:mline (+ cx 3) (+ y 5) (- cx 3) (+ y 11) 7829367 0.0)
    (setq i (1+ i))))

;; Условный трафарет выключателя нагрузки — не изображает расцепитель автомата.
(defun gip:make-qs-block (bn w / i x xmax)
  (if (not (tblsearch "BLOCK" bn))
    (progn
      (setq xmax (* (max 1 w) 50.2))
      (entmake (list '(0 . "BLOCK") (cons 2 bn) '(70 . 0) '(10 0.0 0.0 0.0)))
      (entmake (list '(0 . "LWPOLYLINE") '(100 . "AcDbEntity") '(8 . "0") '(62 . 7) '(100 . "AcDbPolyline") '(90 . 4) '(70 . 1)
                     '(10 2.0 42.0) (cons 10 (list (- xmax 2.0) 42.0)) (cons 10 (list (- xmax 2.0) 182.0)) '(10 2.0 182.0)))
      (setq i 0)
      (while (< i (max 1 w))
        (setq x (+ 25.1 (* i 50.2)))
        (entmake (list '(0 . "LINE") '(100 . "AcDbEntity") '(8 . "0") '(62 . 7) '(100 . "AcDbLine") (list 10 x 10.0 0.0) (list 11 x 42.0 0.0)))
        (entmake (list '(0 . "LINE") '(100 . "AcDbEntity") '(8 . "0") '(62 . 7) '(100 . "AcDbLine") (list 10 x 182.0 0.0) (list 11 x 214.0 0.0)))
        (entmake (list '(0 . "LINE") '(100 . "AcDbEntity") '(8 . "0") '(62 . 7) '(100 . "AcDbLine") (list 10 x 42.0 0.0) (list 11 (+ x 17.0) 112.0 0.0)))
        (entmake (list '(0 . "LINE") '(100 . "AcDbEntity") '(8 . "0") '(62 . 7) '(100 . "AcDbLine") (list 10 (+ x 21.0) 112.0 0.0) (list 11 (+ x 25.0) 112.0 0.0)))
        (setq i (1+ i)))
      (entmake '((0 . "ENDBLK")))))
  (tblsearch "BLOCK" bn))

;; вставка аппарата: блок GIPM_*, атрибуты номинала, метки GIPGEN + GIPDEV(id)
(defun gip:mfill (tpl rt ma In)
  (gip:repl (gip:repl (gip:repl tpl "{R}" (strcat " " rt)) "{M}" (strcat " " ma)) "{I}" (if In (itoa In) "")))
(defun gip:mdev (d x y s is3 / bn obj e rt ma pairs sx vb)
  (setq bn (gip:mblock d s is3) sx (caddr *gip:mo*))
  (if (and (= (gip:g d "kind") "in") (= (gip:g d "inType") "qs") (not (tblsearch "BLOCK" bn))) (gip:make-qs-block bn (gip:g d "w")))
  ;; контактор шире трафарета (ESB40/63 — 3 модуля): растянуть по ширине
  (if (and (= (gip:g d "kind") "km") (gip:g d "st") (setq vb (cdr (assoc (gip:g d "st") *gip:st-vbw*))))
    (setq sx (* sx (/ (* (gip:g d "w") *gip:MW*) vb))))
  (if (not (tblsearch "BLOCK" bn))
    (progn (princ (strcat "\nGIP: нет блока " bn)) nil)
    (progn
      (setq obj (vla-insertblock (gip:ms) (vlax-3d-point (gip:X x) (gip:Y y) 0.0) bn sx (caddr *gip:mo*) (caddr *gip:mo*) 0.0))
      (vla-put-layer obj (gip:layer *gip:mlay*))
      (setq rt (if (gip:g d "In") (gip:rating d) "") ma (strcat (itoa (gip:gn d "idn" (if (= (gip:g d "kind") "fire") 100 30))) "мА"))
      (setq pairs (mapcar '(lambda (p) (cons (car p) (gip:mfill (cdr p) rt ma (gip:g d "In")))) (cdr (assoc bn *gip:mtpl*))))
      (if pairs (gip:set-atts obj pairs))
      (setq e (vlax-vla-object->ename obj))
      (entmod (append (entget e) (list (list -3 (list *gip:app* (cons 1000 *gip:tag*)) (list *gip:dev-app* (cons 1000 (gip:g d "id")))))))
      obj)))

;; ---------------------------------------------------------------- порядок прорисовки
;; таблица порядка прорисовки (ACAD_SORTENTS) пространства/блока owner; mk — создать, если нет
(defun gip:sortents (owner mk / ext st)
  (setq ext (vl-catch-all-apply 'vla-getextensiondictionary (list owner)))
  (if (not (vl-catch-all-error-p ext))
    (progn
      (setq st (vl-catch-all-apply 'vla-getobject (list ext "ACAD_SORTENTS")))
      (if (and (vl-catch-all-error-p st) mk) (setq st (vl-catch-all-apply 'vla-addobject (list ext "ACAD_SORTENTS" "AcDbSortentsTable"))))
      (if (not (vl-catch-all-error-p st)) st))))
;; переместить объекты (enames) на задний (bottom=T) или передний план в owner
(defun gip:draworder (owner enames bottom / st objs arr)
  (setq objs (vl-remove nil (mapcar '(lambda (e) (if (and e (entget e)) (vlax-ename->vla-object e))) enames)))
  (if (and objs (setq st (gip:sortents owner T)))
    (progn
      (setq arr (vlax-make-safearray vlax-vbObject (cons 0 (1- (length objs)))))
      (vlax-safearray-fill arr objs)
      (vl-catch-all-apply (if bottom 'vla-movetobottom 'vla-movetotop) (list st arr)))))
;; объекты, созданные после mark (entlast до рисования)
(defun gip:ents-after (mark / e r)
  (setq e (if mark (entnext mark) (entnext)) r nil)
  (while e (setq r (cons e r) e (entnext e)))
  (reverse r))
;; блоки аппаратов GIPM_* из прежних шаблонов: надписи шли раньше заливок (DEKraft) и закрывались ими —
;; поднять надписи наверх в самом блоке (один раз: у блока появляется таблица порядка прорисовки)
(defun gip:fix-mblocks (/ blks b nm e ed seenT bad late)
  (setq blks (vla-get-blocks (vla-get-activedocument (vlax-get-acad-object))))
  (vlax-for b blks
    (setq nm (vla-get-name b))
    (if (and (wcmatch nm "GIPM_*") (null (gip:sortents b nil)))
      (progn
        (setq e (cdr (assoc -2 (tblsearch "BLOCK" nm))) seenT nil bad nil late nil)
        (while e
          (setq ed (entget e))
          (cond ((= (cdr (assoc 0 ed)) "HATCH") (if seenT (setq bad T)))
                ((member (cdr (assoc 0 ed)) '("TEXT" "MTEXT" "ATTDEF")) (setq seenT T late (cons e late))))
          (setq e (entnext e)))
        ;; заливка идёт после надписи — надписи наверх
        (if bad (gip:draworder b (reverse late) nil))))))

;; ---------------------------------------------------------------- построение монтажной схемы
(defun gip:montage (S BRD Fm / mark0 backs box tall is3 TAGH COMB rails all NR ri acc i d runs cur k jm seen dd chain CONN buses busOrder inD xb fire km c2 rns
                     down INN-k use used ph rs net src g w rn xbSlot lanes trunks TL TR x0 SWD y chY railC hasTag maxH h busY SH bx b nl inc
                     peN peW peX SWX swPts hasSw e PA B2 pts l ya yb xt ly xr ca cb XEXT xa xbx mid ty tx sc BW BH)
  (setq is3 (= (gip:g S "phases") 3) TAGH 50.0 COMB 16.0)
  ;; аппараты: рейка, индекс, смещение, трафарет, высота
  (setq rails nil ri 0)
  (foreach r (gip:g BRD "rails")
    (setq acc 0 i 0 cur nil)
    (foreach d r
      (setq d (gip:s d "rail" ri) d (gip:s d "idx" i) d (gip:s d "xo" (* acc *gip:MW*)))
      (setq d (gip:s d "st" (gip:stencil d S is3)))
      (setq d (gip:s d "h" (if (gip:g d "st") (cadr (assoc (gip:g d "st") *gip:st-term*)) *gip:GH*)))
      (setq acc (+ acc (gip:g d "w")) i (1+ i) cur (append cur (list d))))
    (setq rails (append rails (list cur)) ri (1+ ri)))
  (setq all (apply 'append rails) NR (length rails))
  (setq *gip:mdevs* all)
  (defun gip:m-by (id) (vl-some '(lambda (d) (if (= (gip:g d "id") id) d)) all))
  ;; гребёнки
  (setq runs nil)
  (foreach r rails
    (setq cur nil)
    (foreach d r
      (setq k (gip:comb-key d))
      (if (and k cur (= (gip:g cur "key") k) (= (gip:g cur "feed") (gip:g d "feed")) (setq jm (gip:comb-join cur d)))
        (setq cur (gip:s (gip:s cur "devs" (append (gip:g cur "devs") (list d))) "mode" jm))
        (progn (if cur (setq runs (append runs (list cur))))
               (setq cur (list (cons "key" k) (cons "feed" (gip:g d "feed")) (cons "devs" (list d)) (cons "mode" nil))))))
    (if cur (setq runs (append runs (list cur)))))
  ;; соединения: элементы связи — (dev-id side pole) | ("ext" k) | ("bus" key) | ("sw" n)
  (setq CONN nil buses (list (cons "main" "N общий")) busOrder (list "main"))
  (setq inD (gip:m-by "in") xb (gip:m-by "xb") fire (gip:m-by "fire") km (gip:m-by "km") c2 (gip:m-by "c2"))
  (setq rns (vl-remove-if-not '(lambda (d) (= (gip:g d "kind") "rn")) all))
  (setq INN-k 0)
  (defun gip:m-inn () (if (member "N" (gip:g inD "poles")) (list "in" "bot" "N") (progn (setq INN-k (1+ INN-k)) (list "ext" (1- INN-k)))))
  ;; ввод -> (реле) -> УЗО 100 мА -> кросс-модуль; без кросс-модуля группы питаются от последнего аппарата цепочки, N — от шины
  (setq down (cond (fire (list "fire" "top")) (xb (list "xb" "bot")) (T nil)))
  (defun gip:m-d2 (p) (list (car down) (cadr down) p))
  (defun gip:m-cadd (a b net) (setq CONN (append CONN (list (list a b net)))))
  (if rns
    (progn
      (setq i 0)
      (foreach rn rns
        (setq ph (if is3 (gip:g rn "phase") "L") rs (if (gip:g rn "st") "top" "bot"))
        (gip:m-cadd (list "in" "bot" ph) (list (gip:g rn "id") rs "L") ph)
        (gip:m-cadd (if (= i 0) (gip:m-inn) (list (gip:g (nth (1- i) rns) "id") rs "N")) (list (gip:g rn "id") rs "N") "N")
        (if down (gip:m-cadd (list (gip:g rn "id") "bot" "Lo") (gip:m-d2 ph) ph))
        (setq i (1+ i))))
    (if down (foreach ph (if is3 '("L1" "L2" "L3") '("L")) (gip:m-cadd (list "in" "bot" ph) (gip:m-d2 ph) ph))))
  (gip:m-cadd (gip:m-inn) (if down (gip:m-d2 "N") (list "bus" "main")) "N")
  (if fire
    (if xb
      (foreach p (gip:g fire "poles") (gip:m-cadd (list "fire" "bot" p) (list "xb" "bot" p) (gip:net fire p is3)))
      (gip:m-cadd (list "fire" "bot" "N") (list "bus" "main") "N")))
  (if xb (gip:m-cadd (list "xb" "bot" "N") (list "bus" "main") "N"))
  ;; источник фазы net для групп «от ввода»
  (defun gip:m-src (net d / rn)
    (cond (xb (list "xb" (if (= (gip:g d "rail") (gip:g xb "rail")) "top" "bot") (if (= net "N") "N" (if is3 net "L"))))
          ((= net "N") (list "bus" "main"))
          (fire (list "fire" "bot" (if is3 net "L")))
          ((and rns (setq rn (if is3 (vl-some '(lambda (r) (if (= (gip:g r "phase") net) r)) rns) (car rns)))) (list (gip:g rn "id") "bot" "Lo"))
          (T (list "in" "bot" (if is3 net "L")))))
  ;; подвод к аппарату d (полюс p) участка гребёнки; без кросс-модуля — шлейфом от предыдущего аппарата той же фазы
  ;; (не больше двух проводов в клемме)
  (setq chain nil)
  (defun gip:m-feed (d p / net src e)
    (setq net (gip:net d p is3) src (gip:g d "feed") e (list (gip:g d "id") "top" p))
    (cond ((= src "src")
           (gip:m-cadd (if (and (null xb) (gip:g chain net)) (gip:g chain net) (gip:m-src net d)) e net)
           (if (null xb) (setq chain (gip:s chain net e))))
          ((and (= src "km") km) (if (/= net "N") (gip:m-cadd (list "km" "bot" (if is3 net "L")) (list (gip:g d "id") "top" p) net)))
          ((and src (gip:starts src "rcd")) (if (and (gip:m-by src) (/= net "N")) (gip:m-cadd (list src "bot" (if (= (gip:g (gip:m-by src) "w") 4) net "L")) (list (gip:g d "id") "top" p) net)))))
  (foreach rn runs
    (setq d (car (gip:g rn "devs")))
    (if (not (member (gip:g d "kind") '("in" "rn" "fire" "xb")))
      (progn
        (if (= (gip:g rn "mode") "cyc")
          ;; трёхфазная гребёнка: каждая фаза — к первому аппарату этой фазы, N — один раз
          (progn
            (setq seen nil)
            (foreach dd (gip:g rn "devs")
              (if (not (member (gip:g dd "phase") seen))
                (progn (setq seen (cons (gip:g dd "phase") seen)) (gip:m-feed dd "L"))))
            (if (member "N" (gip:g d "poles")) (gip:m-feed d "N")))
          (foreach p (gip:g d "poles") (if (/= p "A1") (gip:m-feed d p))))
        (if (= (gip:g d "kind") "rcd")
          (progn (setq k (strcat "rcd" (itoa (gip:g d "rcdNo"))))
                 (setq buses (append buses (list (cons k (strcat "N " (gip:g d "ref"))))) busOrder (append busOrder (list k)))
                 (gip:m-cadd (list (gip:g d "id") "bot" "N") (list "bus" k) "N"))))))
  (setq hasSw (and km c2))
  (if hasSw
    (progn (gip:m-cadd (list "c2" "bot" "L") (list "sw" 1) (if is3 "L1" "L"))
           (gip:m-cadd (list "sw" 2) (list "km" "top" "A1") "CTL")
           (gip:m-cadd (list "km" "bot" "A2") (list "bus" "main") "N")))
  ;; точки подключения: каждой связи — своя
  (setq use nil)
  (foreach c CONN (foreach e (list (car c) (cadr c))
                 (if (and (not (member (car e) '("ext" "bus" "sw"))) (/= (gip:g (gip:m-by (car e)) "kind") "xb"))
                   (setq use (gip:s use (gip:join e "|") (1+ (gip:gn use (gip:join e "|") 0)))))))
  (setq used nil xbSlot (list (cons "top" 0) (cons "bot" 0)))
  (defun gip:m-endrel (e / d bars bi n cols x kk barH t1 key nn ii)
    (setq d (gip:m-by (car e)))
    (if (= (gip:g d "kind") "xb")
      (progn
        (setq bars (length (gip:g d "poles")) bi (gip:index (caddr e) (gip:g d "poles"))) (if (null bi) (setq bi 0))
        (setq n (gip:g xbSlot (cadr e)) xbSlot (gip:s xbSlot (cadr e) (1+ n)))
        (setq cols (* (gip:g d "w") 3) x (+ 10 (* (rem n cols) (/ (- (* (gip:g d "w") *gip:MW*) 20) (- cols 1)))))
        (setq kk (/ *gip:MW* 36.0) barH (/ (- *gip:GH* (* 70 kk)) bars))
        (list x (+ (* 35 kk) (* bi barH) (/ barH 2.0)) T))
      (progn
        (setq t1 (gip:term d (cadr e) (caddr e)) key (gip:join e "|") nn (gip:gn use key 1) ii (gip:gn used key 0))
        (setq used (gip:s used key (1+ ii)))
        (list (+ (car t1) (if (> nn 1) (* (- ii (/ (- nn 1) 2.0)) 7.0) 0.0)) (cadr t1) nil))))
  (setq CONN (mapcar '(lambda (c / a b) (setq a (car c) b (cadr c))
                     (list (if (member (car a) '("ext" "bus" "sw")) a (append a (list (gip:m-endrel a))))
                           (if (member (car b) '("ext" "bus" "sw")) b (append b (list (gip:m-endrel b))))
                           (caddr c))) CONN))
  ;; каналы
  (defun gip:m-chof (e) (cond ((= (car e) "ext") 0) ((= (car e) "bus") NR) ((= (car e) "sw") nil)
                        ((= (cadr e) "top") (gip:g (gip:m-by (car e)) "rail")) (T (1+ (gip:g (gip:m-by (car e)) "rail")))))
  (setq lanes (mapcar '(lambda (x) 0) (gip:range (1+ NR))) trunks (list (cons "L" 0) (cons "R" 0)))
  (defun gip:m-lane (ch / v) (setq v (nth ch lanes) lanes (append (gip:take lanes ch) (list (1+ v)) (gip:drop lanes (1+ ch)))) v)
  (setq XEXT (+ (gip:g inD "xo") (* (gip:g inD "w") *gip:MW*) 12))
  (defun gip:m-ex (e) (cond ((= (car e) "bus") nil) ((= (car e) "ext") (+ XEXT (* (cadr e) 8))) (T (+ (gip:g (gip:m-by (car e)) "xo") (car (cadddr e))))))
  (setq CONN (mapcar '(lambda (c / a b ca cb sw e2 la lb side tk xa xbx mid)
                     (setq a (car c) b (cadr c))
                     (if (or (= (car a) "sw") (= (car b) "sw"))
                       (progn (setq e2 (if (= (car a) "sw") b a) ca (gip:m-chof e2))
                              (append c (list (list "sw" ca (gip:m-lane ca) (if (= (car a) "sw") (cadr a) (cadr b))))))
                       (progn
                         (setq ca (gip:m-chof a) cb (gip:m-chof b))
                         (if (= ca cb)
                           (append c (list (list "same" ca (gip:m-lane ca))))
                           (progn
                             (setq la (gip:m-lane ca) lb (gip:m-lane cb) xa (gip:m-ex a) xbx (gip:m-ex b))
                             (setq mid (cond ((null xa) xbx) ((null xbx) xa) (T (/ (+ xa xbx) 2.0))))
                             (setq side (if (< mid (/ (* (gip:g S "railW") *gip:MW*) 2.0)) "L" "R"))
                             (setq tk (gip:g trunks side) trunks (gip:s trunks side (1+ tk)))
                             (append c (list (list "cross" ca cb la lb side tk)))))))) CONN))
  ;; геометрия
  (setq TL (+ 40 (* (gip:g trunks "L") *gip:LANE*)) TR (+ 46 (* (gip:g trunks "R") *gip:LANE*) (if hasSw (+ (* 2 *gip:LANE*) 6) 0)))
  (setq x0 TL SWD (+ TL (* (gip:g S "railW") *gip:MW*) TR))
  (setq y 92.0 chY nil railC nil hasTag nil maxH nil)
  (foreach r rails
    (setq hasTag (append hasTag (list (vl-some '(lambda (d) (gip:g d "line")) r))))
    (setq maxH (append maxH (list (apply 'max (cons *gip:GH* (mapcar '(lambda (d) (gip:g d "h")) r)))))))
  (setq k 0)
  (while (<= k NR)
    (setq h (max 34 (+ 22 (* (nth k lanes) *gip:LANE*))))
    (setq chY (append chY (list (list y h))) y (+ y h))
    (if (< k NR)
      (progn (setq y (+ y COMB) railC (append railC (list (+ y (/ (nth k maxH) 2.0)))))
             (setq y (+ y (nth k maxH) (if (nth k hasTag) (+ TAGH 10) 12)))))
    (setq k (1+ k)))
  (setq busY (+ y 30) SH (+ busY 70))
  ;; масштаб под лист: узкий щит — слева от штампа во всю высоту, широкий — над штампом
  (setq tall (< (/ (+ SWD (if hasSw 150.0 20.0)) SH) (/ 10250.0 13530.0)))
  (setq box (if tall (list (- (car Fm) 19700.0) (+ (cadr Fm) 420.0) (- (car Fm) 9450.0) (+ (cadr Fm) 13950.0))
                     (list (- (car Fm) 19800.0) (+ (cadr Fm) 3050.0) (- (car Fm) 450.0) (+ (cadr Fm) 13950.0))))
  (setq BW (- (caddr box) (car box)) BH (- (cadddr box) (cadr box)))
  (setq sc (min (/ BW (+ SWD (if hasSw 150 20))) (/ BH SH)))
  (setq *gip:mo* (list (+ (car box) (/ (- BW (* (+ SWD (if hasSw 150 20)) sc)) 2.0)) (- (cadddr box) (/ (- BH (* SH sc)) 2.0)) sc))
  (setq *gip:mgeo* (list (cons "mo" *gip:mo*) (cons "x0" x0) (cons "railC" railC) (cons "railW" (gip:g S "railW")) (cons "R" NR)))
  (defun gip:m-laney (ch i) (+ (car (nth ch chY)) 16 (* i *gip:LANE*)))
  (defun gip:m-devtop (d) (- (nth (gip:g d "rail") railC) (/ (gip:g d "h") 2.0)))
  (defun gip:m-p (e / d)
    (cond ((= (car e) "ext") (list (+ x0 (gip:g inD "xo") (* (gip:g inD "w") *gip:MW*) 12 (* (cadr e) 8)) 4.0 "ext"))
          ((= (car e) "bus") (list (gip:m-busterm (cadr e)) (+ busY 4) "bus"))
          (T (setq d (gip:m-by (car e)))
             (list (+ x0 (gip:g d "xo") (car (cadddr e))) (+ (gip:m-devtop d) (cadr (cadddr e))) (cadr e) (caddr (cadddr e))))))
  ;; шины N
  (setq bx (+ x0 4) b nil)
  (setq buses (mapcar '(lambda (k / nm nl inc n w)
                         (setq nm (cdr (assoc k buses)))
                         (setq nl (if (= k "main")
                                    (length (vl-remove-if-not '(lambda (d) (and (gip:g d "line") (not (gip:g d "rcdNo")) (member (gip:g d "kind") '("a1" "a3")))) all))
                                    (length (vl-remove-if-not '(lambda (d) (and (= (strcat "rcd" (itoa (gip:gn d "rcdNo" 0))) k) (gip:g d "line"))) all))))
                         (setq inc (length (vl-remove-if-not '(lambda (c) (and (= (car (cadr c)) "bus") (= (cadr (cadr c)) k))) CONN)))
                         (setq n (max 6 (+ nl inc 1)) w (+ (* n 13) 22))
                         (setq b (list k nm bx n w 0) bx (+ bx w 16))
                         b) busOrder))
  (defun gip:m-busterm (k / bb x)
    (setq bb (assoc k buses) x (+ (nth 2 bb) 15 (* (nth 5 bb) 13)))
    (setq buses (subst (append (gip:take bb 5) (list (1+ (nth 5 bb)))) bb buses))
    x)
  ;; ---- рисование
  (gip:layer *gip:mlay*)
  (vl-catch-all-apply 'gip:fix-mblocks nil)
  (setq mark0 (entlast))
  (gip:mrrect 2.0 2.0 (- SWD 4) (- SH 4) 16.0 9079434)
  (gip:mrrect 22.0 22.0 (- SWD 44) (- SH 44) 8.0 10132122)
  (foreach p (list (list 34.0 34.0) (list (- SWD 34) 34.0) (list 34.0 (- SH 34)) (list (- SWD 34) (- SH 34)))
    (gip:mcircle (car p) (cadr p) 7.0 7829367) (gip:mcircle (car p) (cadr p) 3.0 7829367))
  (foreach c railC
    (gip:mrect (- x0 14) (- c 50) (+ (* (gip:g S "railW") *gip:MW*) 28) 100.0 16053492 11908533)
    (gip:mrect (- x0 14) (- c 17) (+ (* (gip:g S "railW") *gip:MW*) 28) 34.0 14474460 10132122))
  ;; корпус и DIN-рейки — на задний план (под аппараты), независимо от прежних DRAWORDER в чертеже
  (setq backs (gip:ents-after mark0))
  ;; шина PE
  (setq peN (min 26 (max 12 (+ 4 (length (vl-remove-if-not '(lambda (d) (gip:g d "line")) all))))))
  (setq peW (+ (* peN 13) 22) peX (max x0 (- SWD TR peW)))
  (gip:busshape peX 40.0 peN 9291327 6066978)
  (gip:tagbox (- (+ peX (/ peW 2.0)) 56) 72.0 "Шина заземления" 112.0)
  ;; аппараты
  (foreach d all (gip:mdev d (+ x0 (gip:g d "xo")) (gip:m-devtop d) S is3))
  ;; гребёнки
  (foreach rn runs
    (if (> (length (gip:g rn "devs")) 1)
      (progn
        (setq d (car (gip:g rn "devs")) e (last (gip:g rn "devs")))
        (setq xa (+ x0 (gip:g d "xo") 3) xt (- (+ x0 (gip:g e "xo") (* (gip:g e "w") *gip:MW*)) 3))
        (setq ty (- (+ (gip:m-devtop d) (apply 'min (mapcar '(lambda (p) (cadr (gip:term d "top" p))) (gip:g d "poles")))) COMB 4))
        (gip:mrect xa ty (- xt xa) 8.0 12434877 7039851)
        (foreach dd (gip:g rn "devs")
          (foreach p (gip:g dd "poles")
            (if (/= p "A1")
              (progn (setq pts (gip:term dd "top" p))
                     (gip:mrect (- (+ x0 (gip:g dd "xo") (car pts)) 2.5) (+ ty 8) 5.0 (- (+ (gip:m-devtop dd) (cadr pts)) ty 8) 12434877 7039851)))))
        (gip:mtext (+ xa 2) (- ty 3) 11.0 (if (= (gip:g rn "mode") "cyc") (if (= (gip:g rn "key") "2P") "3Ф+N" "3Ф") (gip:g rn "key")) 1118481 0))))
  ;; ввод
  (foreach p (gip:g inD "poles")
    (setq pts (gip:term inD "top" p) xa (+ x0 (gip:g inD "xo") (car pts)) ya (+ (gip:m-devtop inD) (cadr pts)))
    (gip:mwire (list (list xa 4.0) (list xa ya)) (gip:net inD p is3))
    (gip:ferr xa ya (gip:net inD p is3) T))
  (gip:tagbox (- (+ x0 (gip:g inD "xo")) 4) 40.0 (if is3 "Ввод 3Ф+N" "Ввод 1Ф+N") 86.0)
  ;; провода
  (setq SWX (+ (- SWD TR) (* (gip:g trunks "R") *gip:LANE*) 30) swPts nil)
  (foreach c CONN
    (setq net (caddr c) g (nth 3 c))
    (cond
      ((= (car g) "sw")
       (setq e (if (= (car (car c)) "sw") (cadr c) (car c)) PA (gip:m-p e) ly (gip:m-laney (cadr g) (caddr g)) xr (+ SWX (* (1- (cadddr g)) *gip:LANE*)))
       (setq swPts (gip:s swPts (itoa (cadddr g)) (list xr ly)))
       (gip:mwire (list (list (car PA) (cadr PA)) (list (car PA) ly) (list xr ly)) net)
       (gip:end-mark PA net))
      (T
       (setq PA (gip:m-p (car c)) B2 (gip:m-p (cadr c)))
       (if (= (car g) "same")
         (progn (setq l (gip:m-laney (cadr g) (caddr g)))
                (setq pts (list (list (car PA) (cadr PA)) (list (car PA) l) (list (car B2) l) (list (car B2) (cadr B2)))))
         (progn (setq ya (gip:m-laney (nth 1 g) (nth 3 g)) yb (gip:m-laney (nth 2 g) (nth 4 g)))
                (setq xt (if (= (nth 5 g) "L") (- TL 16 (* (nth 6 g) *gip:LANE*)) (+ x0 (* (gip:g S "railW") *gip:MW*) 20 (* (nth 6 g) *gip:LANE*))))
                (setq pts (list (list (car PA) (cadr PA)) (list (car PA) ya) (list xt ya) (list xt yb) (list (car B2) yb) (list (car B2) (cadr B2))))))
       (gip:mwire pts net)
       (gip:end-mark PA net) (gip:end-mark B2 net))))
  (if (and (gip:g swPts "1") (gip:g swPts "2"))
    (progn
      (setq PA (gip:g swPts "1") B2 (gip:g swPts "2"))
      (setq ty (+ (min (cadr PA) (cadr B2)) (/ (abs (- (cadr PA) (cadr B2))) 2.0)) tx (+ SWD 8))
      (gip:mwire (list PA (list (+ tx 30) (cadr PA)) (list (+ tx 30) ty)) (if is3 "L1" "L"))
      (gip:mwire (list B2 (list (+ tx 44) (cadr B2)) (list (+ tx 44) ty)) "CTL")
      (gip:tagbox tx (- ty 2) "Клавиша «Мастер выкл»" 110.0)))
  ;; шины N
  (foreach bb buses
    (gip:busshape (nth 2 bb) busY (max (nth 3 bb) (1+ (nth 5 bb))) 2730721 1732520)
    (gip:tagbox (- (+ (nth 2 bb) (/ (nth 4 bb) 2.0)) 44) (+ busY 34) (nth 1 bb) 88.0))
  ;; бирки
  (foreach d all
    (setq w (* (gip:g d "w") *gip:MW*))
    (if (gip:g d "line")
      (gip:loadtag (+ x0 (gip:g d "xo") 2) (+ (nth (gip:g d "rail") railC) (/ (nth (gip:g d "rail") maxH) 2.0) 6) (- w 4) TAGH d)
      (gip:facetag (+ x0 (gip:g d "xo")) (+ (gip:m-devtop d) (* (gip:g d "h") 0.56)) w d)))
  (vl-catch-all-apply 'gip:draworder (list (gip:ms) backs T))
  all)

(defun gip:end-mark (p net)
  (cond ((= (caddr p) "ext") nil)
        ((= (caddr p) "bus") (gip:ferr (car p) (cadr p) net T))
        ((cadddr p) (gip:mdisk (car p) (cadr p) 3.4 16777215) (gip:mcircle (car p) (cadr p) 3.4 3355443))
        (T (gip:ferr (car p) (cadr p) net (= (caddr p) "top")))))
