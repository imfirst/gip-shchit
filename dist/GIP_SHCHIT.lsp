;;; GIP-ЩИТ для AutoCAD 2021–2024 (gipproekt.ru). Строки в коде — ASCII (\U+XXXX), русский только в комментариях.
;;; ============================================================================
;;; GIP-ЩИТ для AutoCAD 2021–2024 — проектирование квартирного щита ГИП
;;; Общие функции: строки, списки, числа, декодирование \U+XXXX
;;; ============================================================================
(vl-load-com)

;; Декодирование строк вида "\U+041F\U+0440..." (все русские строки в файле записаны так,
;; чтобы файл оставался ASCII и одинаково читался при любой кодировке).
(defun gip:hex (s / n i c v)
  (setq n 0 i 1)
  (while (<= i (strlen s))
    (setq c (ascii (strcase (substr s i 1))))
    (setq v (if (<= c 57) (- c 48) (- c 55)))
    (setq n (+ (* n 16) v) i (1+ i)))
  n)

(defun gip:u (s / r i n p)
  (if (and (= (type s) 'STR) (vl-string-search "\\U+" s))
    (progn
      (setq r "" i 0 n (strlen s))
      (while (setq p (vl-string-search "\\U+" s i))
        (setq r (strcat r (substr s (1+ i) (- p i)) (chr (gip:hex (substr s (+ p 4) 4))))
              i (+ p 7)))
      (strcat r (substr s (1+ i))))
    s))

(defun gip:deep-u (x)
  (cond ((= (type x) 'STR) (gip:u x))
        ((and (listp x) x (vl-consp x) (not (listp (cdr x))))
         (cons (gip:deep-u (car x)) (gip:deep-u (cdr x))))
        ((listp x) (mapcar 'gip:deep-u x))
        (T x)))

;; ---------------------------------------------------------------- ассоц. списки
(defun gip:g (a k) (cdr (assoc k a)))
(defun gip:s (a k v / p)
  (if (setq p (assoc k a))
    (subst (cons k v) p a)
    (append a (list (cons k v)))))
(defun gip:gn (a k d / v) (if (setq v (gip:g a k)) v d))
(defun gip:nz (v d) (if v v d))

;; ---------------------------------------------------------------- строки
(defun gip:split (s sep / r p n)
  (setq r nil n (strlen sep))
  (while (setq p (vl-string-search sep s))
    (setq r (cons (substr s 1 p) r) s (substr s (+ p n 1))))
  (reverse (cons s r)))

(defun gip:join (l sep / r)
  (setq r "")
  (foreach x l (setq r (if (= r "") x (strcat r sep x))))
  r)

(defun gip:repl (s old new / r p n)
  (setq r "" n (strlen old))
  (while (setq p (vl-string-search old s))
    (setq r (strcat r (substr s 1 p) new) s (substr s (+ p n 1))))
  (strcat r s))

(defun gip:trim (s) (vl-string-trim " \t\n\r" s))
(defun gip:lower (s) (strcase s T))
(defun gip:has (s p) (if (vl-string-search p s) T nil))
(defun gip:starts (s p) (and (>= (strlen s) (strlen p)) (= (substr s 1 (strlen p)) p)))
(defun gip:ends (s p) (and (>= (strlen s) (strlen p)) (= (substr s (1+ (- (strlen s) (strlen p)))) p)))

;; перенос по словам (как dxWrap)
(defun gip:wrap (txt mx / out cur w)
  (setq out nil cur "")
  (foreach w (gip:split txt " ")
    (if (<= (strlen (gip:trim (strcat cur " " w))) mx)
      (setq cur (gip:trim (strcat cur " " w)))
      (progn (if (/= cur "") (setq out (cons cur out))) (setq cur w))))
  (if (/= cur "") (setq out (cons cur out)))
  (reverse out))

(defun gip:take (l n / r)
  (setq r nil)
  (while (and l (> n 0)) (setq r (cons (car l) r) l (cdr l) n (1- n)))
  (reverse r))
(defun gip:drop (l n) (while (and l (> n 0)) (setq l (cdr l) n (1- n))) l)

;; ---------------------------------------------------------------- числа
(defun gip:round (x) (if (minusp x) (- (fix (+ (- x) 0.5))) (fix (+ x 0.5))))
(defun gip:pad0 (s n) (while (< (strlen s) n) (setq s (strcat "0" s))) s)

;; x с d знаками после запятой, десятичный разделитель — запятая
(defun gip:fmt (x d / k n neg ip fp)
  (setq k (expt 10 d) n (gip:round (* x k)) neg (minusp n) n (abs n))
  (setq ip (/ n k) fp (rem n k))
  (strcat (if (and neg (> n 0)) "-" "") (itoa ip) (if (> d 0) (strcat "," (gip:pad0 (itoa fp) d)) "")))
(defun gip:f1 (x) (gip:fmt x 1))
;; без хвостовых нулей
(defun gip:fmtz (x d / s)
  (setq s (gip:fmt x d))
  (if (vl-string-search "," s)
    (progn (setq s (vl-string-right-trim "0" s)) (if (gip:ends s ",") (setq s (substr s 1 (1- (strlen s)))))))
  s)
;; число в строку с точкой (для служебных целей)
(defun gip:num (x) (if (= (type x) 'INT) (itoa x) (gip:repl (gip:fmtz x 6) "," ".")))
(defun gip:ceil (x / f) (setq f (fix x)) (if (> x f) (1+ f) f))

;; ---------------------------------------------------------------- сортировка (устойчивая, без потерь)
(defun gip:msort (l f / a b n h)
  (if (or (null l) (null (cdr l)))
    l
    (progn
      (setq n (/ (length l) 2) a (gip:take l n) b (gip:drop l n))
      (gip:merge (gip:msort a f) (gip:msort b f) f))))
(defun gip:merge (a b f / r)
  (setq r nil)
  (while (and a b)
    (if (apply f (list (car b) (car a)))
      (setq r (cons (car b) r) b (cdr b))
      (setq r (cons (car a) r) a (cdr a))))
  (append (reverse r) a b))

(defun gip:index (x l / i r)
  (setq i 0 r nil)
  (while (and l (not r)) (if (equal (car l) x) (setq r i)) (setq i (1+ i) l (cdr l)))
  r)
(defun gip:sum (l) (if l (apply '+ l) 0))
(defun gip:filter (f l) (vl-remove-if-not f l))
(defun gip:range (n / r) (setq r nil) (while (> n 0) (setq n (1- n) r (cons n r))) r)

;;; ---- строковые константы
(setq $Q1 (gip:deep-u '("a1" . "\\U+0412\\U+041047-29 1\\U+0420 C{I}")))
(setq $Q2 (gip:deep-u '("a2" . "\\U+0412\\U+041047-29 2\\U+0420 C{I}")))
(setq $Q3 (gip:deep-u '("a3" . "\\U+0412\\U+041047-29 3\\U+0420 C{I}")))
(setq $Q4 (gip:deep-u '("a4" . "\\U+0412\\U+041047-29 4\\U+0420 C{I}")))
(setq $Q5 (gip:deep-u '("dif" . "\\U+0410\\U+0412\\U+0414\\U+042232 C{I} 30\\U+043C\\U+0410")))
(setq $Q6 (gip:deep-u '("dif4" . "\\U+0410\\U+0412\\U+0414\\U+042234 C{I} 30\\U+043C\\U+0410")))
(setq $Q7 (gip:deep-u '("rcd2" . "\\U+0412\\U+04141-63 2\\U+0420 {I}\\U+0410 30\\U+043C\\U+0410")))
(setq $Q8 (gip:deep-u '("rcd4" . "\\U+0412\\U+04141-63 4\\U+0420 {I}\\U+0410 30\\U+043C\\U+0410")))
(setq $Q9 (gip:deep-u '("fire2" . "\\U+0412\\U+04141-63 2\\U+0420 {I}\\U+0410 100\\U+043C\\U+0410")))
(setq $Q10 (gip:deep-u '("fire4" . "\\U+0412\\U+04141-63 4\\U+0420 {I}\\U+0410 100\\U+043C\\U+0410")))
(setq $Q11 (gip:deep-u '("km2" . "\\U+041A\\U+041C63-20\\U+041C 25\\U+0410")))
(setq $Q12 (gip:deep-u '("km4" . "\\U+041A\\U+041C63-40\\U+041C 25\\U+0410")))
(setq $Q13 (gip:deep-u '("a1" . "\\U+0412\\U+0410-101 1P C{I}")))
(setq $Q14 (gip:deep-u '("a2" . "\\U+0412\\U+0410-101 2P C{I}")))
(setq $Q15 (gip:deep-u '("a3" . "\\U+0412\\U+0410-101 3P C{I}")))
(setq $Q16 (gip:deep-u '("a4" . "\\U+0412\\U+0410-101 4P C{I}")))
(setq $Q17 (gip:deep-u '("dif" . "\\U+0414\\U+0418\\U+0424-103 1P+N C{I} 30\\U+043C\\U+0410")))
(setq $Q18 (gip:deep-u '("dif4" . "\\U+0414\\U+0418\\U+0424-103 3P+N C{I} 30\\U+043C\\U+0410")))
(setq $Q19 (gip:deep-u '("rcd2" . "\\U+0423\\U+0417\\U+041E-03 2P {I}\\U+0410 30\\U+043C\\U+0410")))
(setq $Q20 (gip:deep-u '("rcd4" . "\\U+0423\\U+0417\\U+041E-03 4P {I}\\U+0410 30\\U+043C\\U+0410")))
(setq $Q21 (gip:deep-u '("fire2" . "\\U+0423\\U+0417\\U+041E-03 2P {I}\\U+0410 100\\U+043C\\U+0410")))
(setq $Q22 (gip:deep-u '("fire4" . "\\U+0423\\U+0417\\U+041E-03 4P {I}\\U+0410 100\\U+043C\\U+0410")))
(setq $Q23 (gip:deep-u '("km2" . "\\U+041A\\U+041C-103 25\\U+0410 2\\U+041D\\U+041E")))
(setq $Q24 (gip:deep-u '("km4" . "\\U+041A\\U+041C-103 25\\U+0410 4\\U+041D\\U+041E")))
(setq $Q25 (gip:deep-u '("dif" . "NB2LE C{I} 30\\U+043C\\U+0410")))
(setq $Q26 (gip:deep-u '("dif4" . "NB2LE 4P C{I} 30\\U+043C\\U+0410")))
(setq $Q27 (gip:deep-u '("rcd2" . "NXL-63 2P {I}A 30\\U+043C\\U+0410")))
(setq $Q28 (gip:deep-u '("rcd4" . "NXL-63 4P {I}A 30\\U+043C\\U+0410")))
(setq $Q29 (gip:deep-u '("fire2" . "NXL-63 2P {I}A 100\\U+043C\\U+0410")))
(setq $Q30 (gip:deep-u '("fire4" . "NXL-63 4P {I}A 100\\U+043C\\U+0410")))
(setq $Q31 (gip:deep-u '("name" . "\\U+0421\\U+0442\\U+0443\\U+0434\\U+0438\\U+044F")))
(setq $S32 (gip:u "\\U+041F\\U+0440\\U+0438\\U+0445\\U+043E\\U+0436\\U+0430\\U+044F"))
(setq $S33 (gip:u "\\U+041A\\U+0443\\U+0445\\U+043D\\U+044F-\\U+0433\\U+043E\\U+0441\\U+0442\\U+0438\\U+043D\\U+0430\\U+044F"))
(setq $S34 (gip:u "\\U+0421\\U+0430\\U+043D\\U+0443\\U+0437\\U+0435\\U+043B"))
(setq $S35 (gip:u "\\U+0420\\U+043E\\U+0437\\U+0435\\U+0442\\U+043A\\U+0438 \\U+043A\\U+0443\\U+0445\\U+043D\\U+0438"))
(setq $S36 (gip:u "\\U+0420\\U+043E\\U+0437\\U+0435\\U+0442\\U+043A\\U+0438 \\U+0433\\U+043E\\U+0441\\U+0442\\U+0438\\U+043D\\U+043E\\U+0439 \\U+0437\\U+043E\\U+043D\\U+044B"))
(setq $S37 (gip:u "\\U+0420\\U+043E\\U+0437\\U+0435\\U+0442\\U+043A\\U+0438 \\U+0441\\U+0430\\U+043D\\U+0443\\U+0437\\U+043B\\U+0430"))
(setq $Q38 (gip:deep-u '("name" . "1-\\U+043A\\U+043E\\U+043C\\U+043D\\U+0430\\U+0442\\U+043D\\U+0430\\U+044F")))
(setq $S39 (gip:u "\\U+041A\\U+0443\\U+0445\\U+043D\\U+044F"))
(setq $S40 (gip:u "\\U+041A\\U+043E\\U+043C\\U+043D\\U+0430\\U+0442\\U+0430"))
(setq $S41 (gip:u "\\U+0420\\U+043E\\U+0437\\U+0435\\U+0442\\U+043A\\U+0438 \\U+043A\\U+043E\\U+043C\\U+043D\\U+0430\\U+0442\\U+044B"))
(setq $S42 (gip:u "\\U+0420\\U+043E\\U+0437\\U+0435\\U+0442\\U+043A\\U+0438 \\U+043F\\U+0440\\U+0438\\U+0445\\U+043E\\U+0436\\U+0435\\U+0439"))
(setq $Q43 (gip:deep-u '("name" . "2-\\U+043A\\U+043E\\U+043C\\U+043D\\U+0430\\U+0442\\U+043D\\U+0430\\U+044F")))
(setq $S44 (gip:u "\\U+0413\\U+043E\\U+0441\\U+0442\\U+0438\\U+043D\\U+0430\\U+044F"))
(setq $S45 (gip:u "\\U+0421\\U+043F\\U+0430\\U+043B\\U+044C\\U+043D\\U+044F"))
(setq $S46 (gip:u "\\U+0420\\U+043E\\U+0437\\U+0435\\U+0442\\U+043A\\U+0438 \\U+0433\\U+043E\\U+0441\\U+0442\\U+0438\\U+043D\\U+043E\\U+0439"))
(setq $S47 (gip:u "\\U+0420\\U+043E\\U+0437\\U+0435\\U+0442\\U+043A\\U+0438 \\U+0441\\U+043F\\U+0430\\U+043B\\U+044C\\U+043D\\U+0438"))
(setq $Q48 (gip:deep-u '("name" . "3-\\U+043A\\U+043E\\U+043C\\U+043D\\U+0430\\U+0442\\U+043D\\U+0430\\U+044F")))
(setq $S49 (gip:u "\\U+0414\\U+0435\\U+0442\\U+0441\\U+043A\\U+0430\\U+044F"))
(setq $S50 (gip:u "\\U+0421\\U+0430\\U+043D\\U+0443\\U+0437\\U+0435\\U+043B 1"))
(setq $S51 (gip:u "\\U+0421\\U+0430\\U+043D\\U+0443\\U+0437\\U+0435\\U+043B 2"))
(setq $S52 (gip:u "\\U+0420\\U+043E\\U+0437\\U+0435\\U+0442\\U+043A\\U+0438 \\U+0434\\U+0435\\U+0442\\U+0441\\U+043A\\U+043E\\U+0439"))
(setq $S53 (gip:u "\\U+0420\\U+043E\\U+0437\\U+0435\\U+0442\\U+043A\\U+0438 \\U+0441\\U+0430\\U+043D\\U+0443\\U+0437\\U+043B\\U+0430 1"))
(setq $S54 (gip:u "\\U+0420\\U+043E\\U+0437\\U+0435\\U+0442\\U+043A\\U+0438 \\U+0441\\U+0430\\U+043D\\U+0443\\U+0437\\U+043B\\U+0430 2"))
(setq $Q55 (gip:deep-u '((6 . "3\\U+00D71,5") (10 . "3\\U+00D71,5") (16 . "3\\U+00D72,5") (20 . "3\\U+00D72,5") (25 . "3\\U+00D74") (32 . "3\\U+00D76") (40 . "3\\U+00D710") (50 . "3\\U+00D710") (63 . "3\\U+00D716"))))
(setq $Q56 (gip:deep-u '((10 . "5\\U+00D71,5") (16 . "5\\U+00D72,5") (20 . "5\\U+00D72,5") (25 . "5\\U+00D74") (32 . "5\\U+00D76") (40 . "5\\U+00D710") (50 . "5\\U+00D710") (63 . "5\\U+00D716"))))
(setq $Q57 (gip:deep-u '(("abb" . "ESB{K}N") ("iek" . "\\U+041A\\U+041C63-{C}0\\U+041C {I}\\U+0410") ("dekraft" . "\\U+041A\\U+041C-103 {I}\\U+0410 {C}\\U+041D\\U+041E") ("chint" . "NCH8-{I}/{C}0"))))
(setq $Q58 (gip:deep-u '("\\U+041F\\U+043E\\U+0442\\U+043E\\U+043B\\U+043E\\U+043A" "\\U+041F\\U+043E\\U+043B, \\U+043F\\U+043E\\U+0442\\U+043E\\U+043B\\U+043E\\U+043A" "\\U+041A\\U+0430\\U+0431\\U+0435\\U+043B\\U+044C-\\U+043A\\U+0430\\U+043D\\U+0430\\U+043B")))
(setq $S59 (gip:u "5\\U+00D71,5"))
(setq $S60 (gip:u "3\\U+00D71,5"))
(setq $S61 (gip:u "\\U+043F\\U+043E \\U+0440\\U+0430\\U+0441\\U+0447\\U+0451\\U+0442\\U+0443"))
(setq $S62 (gip:u "\\U+0429\\U+0420"))
(setq $S63 (gip:u "\\U+0420"))
(setq $S64 (gip:u "\\U+041F\\U+043E\\U+0442\\U+043E\\U+043B\\U+043E\\U+043A"))
(setq $S65 (gip:u "\\U+041E\\U+0441\\U+0432\\U+0435\\U+0449\\U+0435\\U+043D\\U+0438\\U+0435: "))
(setq $S66 (gip:u "\\U+0412\\U+0430\\U+0440\\U+043E\\U+0447\\U+043D\\U+0430\\U+044F \\U+043F\\U+0430\\U+043D\\U+0435\\U+043B\\U+044C"))
(setq $S67 (gip:u "\\U+0414\\U+0443\\U+0445\\U+043E\\U+0432\\U+043E\\U+0439 \\U+0448\\U+043A\\U+0430\\U+0444"))
(setq $S68 (gip:u "\\U+0425\\U+043E\\U+043B\\U+043E\\U+0434\\U+0438\\U+043B\\U+044C\\U+043D\\U+0438\\U+043A"))
(setq $S69 (gip:u "\\U+041F\\U+041C\\U+041C \\U+0438 \\U+0438\\U+0437\\U+043C\\U+0435\\U+043B\\U+044C\\U+0447\\U+0438\\U+0442\\U+0435\\U+043B\\U+044C"))
(setq $S70 (gip:u "\\U+0421\\U+0442\\U+0438\\U+0440\\U+0430\\U+043B\\U+044C\\U+043D\\U+0430\\U+044F \\U+043C\\U+0430\\U+0448\\U+0438\\U+043D\\U+0430"))
(setq $S71 (gip:u "\\U+0421\\U+0443\\U+0448\\U+0438\\U+043B\\U+044C\\U+043D\\U+0430\\U+044F \\U+043C\\U+0430\\U+0448\\U+0438\\U+043D\\U+0430"))
(setq $S72 (gip:u "\\U+0422\\U+0451\\U+043F\\U+043B\\U+044B\\U+0439 \\U+043F\\U+043E\\U+043B"))
(setq $S73 (gip:u "\\U+0412\\U+043E\\U+0434\\U+043E\\U+043D\\U+0430\\U+0433\\U+0440\\U+0435\\U+0432\\U+0430\\U+0442\\U+0435\\U+043B\\U+044C \\U+043D\\U+0430\\U+043A\\U+043E\\U+043F\\U+0438\\U+0442\\U+0435\\U+043B\\U+044C\\U+043D\\U+044B\\U+0439"))
(setq $S74 (gip:u "\\U+0412\\U+043E\\U+0434\\U+043E\\U+043D\\U+0430\\U+0433\\U+0440\\U+0435\\U+0432\\U+0430\\U+0442\\U+0435\\U+043B\\U+044C \\U+043F\\U+0440\\U+043E\\U+0442\\U+043E\\U+0447\\U+043D\\U+044B\\U+0439"))
(setq $S75 (gip:u "\\U+0417\\U+0430\\U+0449\\U+0438\\U+0442\\U+0430 \\U+043E\\U+0442 \\U+043F\\U+0440\\U+043E\\U+0442\\U+0435\\U+0447\\U+0435\\U+043A \\U+0438 \\U+0441\\U+043B\\U+0430\\U+0431\\U+043E\\U+0442\\U+043E\\U+0447\\U+043D\\U+044B\\U+0439 \\U+0449\\U+0438\\U+0442"))
(setq $S76 (gip:u "\\U+041A\\U+043E\\U+043D\\U+0434\\U+0438\\U+0446\\U+0438\\U+043E\\U+043D\\U+0435\\U+0440"))
(setq $Q77 (gip:deep-u '(lambda (l / o kv)
                     (setq o (gip:g edit (gip:g l "id")))
                     (foreach kv o (setq l (gip:s l (car kv) (cdr kv))))
                     (setq l (gip:s l "cable" (if (gip:g o "cable") (gip:g o "cable") (gip:cable-for (gip:g l "In") (gip:g l "poles") (= (gip:g l "cat") "light")))))
                     (if (and (= (gip:g l "cat") "hob") (= (gip:g l "poles") 3) (not (gip:g o "cable"))) (setq l (gip:s l "cable" "5\\U+00D74")))
                     l)))
(setq $Q78 (gip:deep-u '("name" . "\\U+0412\\U+0432\\U+043E\\U+0434\\U+043D\\U+043E\\U+0439 \\U+0430\\U+0432\\U+0442\\U+043E\\U+043C\\U+0430\\U+0442")))
(setq $Q79 (gip:deep-u '("model" . "VIP-63 63\\U+0410")))
(setq $S80 (gip:u "\\U+0420\\U+0435\\U+043B\\U+0435 \\U+043D\\U+0430\\U+043F\\U+0440\\U+044F\\U+0436\\U+0435\\U+043D\\U+0438\\U+044F "))
(setq $Q81 (gip:deep-u '("name" . "\\U+0420\\U+0435\\U+043B\\U+0435 \\U+043D\\U+0430\\U+043F\\U+0440\\U+044F\\U+0436\\U+0435\\U+043D\\U+0438\\U+044F")))
(setq $Q82 (gip:deep-u '("name" . "\\U+0423\\U+0417\\U+041E \\U+043F\\U+0440\\U+043E\\U+0442\\U+0438\\U+0432\\U+043E\\U+043F\\U+043E\\U+0436\\U+0430\\U+0440\\U+043D\\U+043E\\U+0435 100 \\U+043C\\U+0410")))
(setq $S83 (gip:u "4\\U+041F, 125 \\U+0410"))
(setq $S84 (gip:u "2\\U+041F, 125 \\U+0410"))
(setq $Q85 (gip:deep-u '("name" . "\\U+041A\\U+0440\\U+043E\\U+0441\\U+0441-\\U+043C\\U+043E\\U+0434\\U+0443\\U+043B\\U+044C")))
(setq $Q86 (gip:deep-u '("brand" . "\\U+2014")))
(setq $Q87 (gip:deep-u '("name" . "\\U+0417\\U+0430\\U+0449\\U+0438\\U+0442\\U+0430 \\U+043A\\U+0430\\U+0442\\U+0443\\U+0448\\U+043A\\U+0438 \\U+041A\\U+041C")))
(setq $Q88 (gip:deep-u '("name" . "\\U+041A\\U+043E\\U+043D\\U+0442\\U+0430\\U+043A\\U+0442\\U+043E\\U+0440 \\U+00AB\\U+043C\\U+0430\\U+0441\\U+0442\\U+0435\\U+0440-\\U+0432\\U+044B\\U+043A\\U+043B\\U+044E\\U+0447\\U+0430\\U+0442\\U+0435\\U+043B\\U+044C\\U+00BB")))
(setq $S89 (gip:u "\\U+0423\\U+0417\\U+041E \\U+0433\\U+0440\\U+0443\\U+043F\\U+043F\\U+044B "))
(setq $S90 (gip:u "\\U+041B\\U+0410\\U+041E"))
(setq $S91 (gip:u "\\U+041B\\U+041E"))
(setq $S92 (gip:u "\\U+041B\\U+0421"))
(setq $S93 (gip:u "5\\U+00D74"))
(setq $S94 (gip:u "\\U+00D7"))
(setq $S95 (gip:u "\\U+0413\\U+0440\\U+0443\\U+043F\\U+043F\\U+0430"))
(setq $S96 (gip:u "30\\U+043C\\U+0410"))
(setq $S97 (gip:u "\\U+043C\\U+0410"))
(setq $S98 (gip:u "\\U+0412\\U+0412\\U+0413\\U+043D\\U+0433(\\U+0410)-LS"))
(setq $Q99 (gip:deep-u '(lambda (r / nm) (setq nm (gip:gn r "name" "")) (if (gip:starts nm "\\U+041E\\U+0441\\U+0432\\U+0435\\U+0449\\U+0435\\U+043D\\U+0438\\U+0435: ") (substr nm 12) nm))))
(setq $S100 (gip:u "\nGIP-\\U+0429\\U+0418\\U+0422: \\U+043D\\U+0435\\U+0442 \\U+0434\\U+0430\\U+043D\\U+043D\\U+044B\\U+0445 \\U+0438\\U+0437 \\U+043F\\U+0430\\U+043D\\U+0435\\U+043B\\U+0438."))
(setq $S101 (gip:u "\nGIP: \\U+043D\\U+0435\\U+0442 \\U+043F\\U+0440\\U+043E\\U+0442\\U+043E\\U+0442\\U+0438\\U+043F\\U+0430 "))
(setq $S102 (gip:u "\nGIP: \\U+043D\\U+0435 \\U+0441\\U+043E\\U+0437\\U+0434\\U+0430\\U+043D \\U+043E\\U+0431\\U+044A\\U+0435\\U+043A\\U+0442 "))
(setq $S103 (gip:u "\nGIP: \\U+0441\\U+0432\\U+043E\\U+0439\\U+0441\\U+0442\\U+0432\\U+043E "))
(setq $Q104 (gip:deep-u '("\\U+042D\\U+041E\\U+041C_\\U+0420\\U+043E\\U+0437\\U+0435\\U+0442\\U+043A\\U+0438_GIP" "\\U+042D\\U+041E\\U+041C_\\U+0429\\U+0438\\U+0442\\U+044B_GIP" "\\U+042D\\U+041E\\U+041C_\\U+0421\\U+0432\\U+0435\\U+0442\\U+0438\\U+043B\\U+044C\\U+043D\\U+0438\\U+043A\\U+0438_GIP" "\\U+042D\\U+041E\\U+041C_\\U+0412\\U+044B\\U+043A\\U+043B\\U+044E\\U+0447\\U+0430\\U+0442\\U+0435\\U+043B\\U+0438_GIP" "\\U+042D\\U+041E\\U+041C_\\U+0421\\U+0445\\U+0435\\U+043C\\U+0430 \\U+043F\\U+043E\\U+0434\\U+0432\\U+043E\\U+0434\\U+0430 \\U+043A\\U+0430\\U+0431\\U+0435\\U+043B\\U+044F_GIP")))
(setq $S105 (gip:u "\\U+0412\\U+0438\\U+0434"))
(setq $S106 (gip:u "\\U+04103-GIP-ALBOM"))
(setq $S107 (gip:u "\\U+0420\\U+0430\\U+0437\\U+0434\\U+0435\\U+043B \\U+041F\\U+0414"))
(setq $S108 (gip:u "\\U+0412\\U+044B\\U+043A\\U+043B\\U+044E\\U+0447\\U+0430\\U+0442\\U+0435\\U+043B\\U+044C \\U+0441\\U+043A\\U+0440\\U+044B\\U+0442\\U+043E\\U+0439 \\U+0443\\U+0441\\U+0442\\U+0430\\U+043D\\U+043E\\U+0432\\U+043A\\U+0438"))
(setq $S109 (gip:u "\\U+0442\\U+0438\\U+043F"))
(setq $S110 (gip:u ": \\U+0432\\U+0438\\U+0434\\U+0438\\U+043C\\U+043E\\U+0441\\U+0442\\U+044C \\U+00AB"))
(setq $S111 (gip:u "\\U+00BB \\U+2014 "))
(setq $S112 (gip:u "\nGIP: \\U+0432 \\U+0447\\U+0435\\U+0440\\U+0442\\U+0435\\U+0436\\U+0435 \\U+043D\\U+0435\\U+0442 \\U+0431\\U+043B\\U+043E\\U+043A\\U+0430 \\U+00AB"))
(setq $S113 (gip:u "\\U+00BB \\U+2014 \\U+043E\\U+0442\\U+043A\\U+0440\\U+043E\\U+0439\\U+0442\\U+0435 \\U+0448\\U+0430\\U+0431\\U+043B\\U+043E\\U+043D \\U+0413\\U+0418\\U+041F"))
(setq $Q114 (gip:deep-u '(" 1P+N" " 3P+N" " 1P" " 2P" " 3P" " 4P" " 1\\U+0420" " 2\\U+0420" " 3\\U+0420" " 4\\U+0420")))
(setq $S115 (gip:u "(\\U+0410)"))
(setq $S116 (gip:u "\\U+0412\\U+0412\\U+0413\\U+043D\\U+0433LS "))
(setq $S117 (gip:u "\\U+041F16"))
(setq $S118 (gip:u "\\U+041F20"))
(setq $S119 (gip:u "\\U+041F25"))
(setq $S120 (gip:u "\\U+041F32"))
(setq $S121 (gip:u "\\U+0441\\U+0430\\U+043D\\U+0443\\U+0437"))
(setq $S122 (gip:u "\\U+0432\\U+0430\\U+043D\\U+043D"))
(setq $S123 (gip:u "\\U+0434\\U+0443\\U+0448"))
(setq $S124 (gip:u "\\U+0442\\U+0443\\U+0430\\U+043B\\U+0435\\U+0442"))
(setq $S125 (gip:u "\\U+0441/\\U+0443"))
(setq $S126 (gip:u "\\U+0410\\U+0432\\U+0442\\U+043E\\U+043C\\U+0430\\U+0442\\U+0438\\U+0447\\U+0435\\U+0441\\U+043A\\U+0438\\U+0439 \\U+0432\\U+044B\\U+043A\\U+043B\\U+044E\\U+0447\\U+0430\\U+0442\\U+0435\\U+043B\\U+044C "))
(setq $Q127 (gip:deep-u '("\\U+043E\\U+0434\\U+043D\\U+043E\\U+043F\\U+043E\\U+043B\\U+044E\\U+0441\\U+043D\\U+044B\\U+0439" "\\U+0434\\U+0432\\U+0443\\U+0445\\U+043F\\U+043E\\U+043B\\U+044E\\U+0441\\U+043D\\U+044B\\U+0439" "\\U+0442\\U+0440\\U+0435\\U+0445\\U+043F\\U+043E\\U+043B\\U+044E\\U+0441\\U+043D\\U+044B\\U+0439" "\\U+0447\\U+0435\\U+0442\\U+044B\\U+0440\\U+0435\\U+0445\\U+043F\\U+043E\\U+043B\\U+044E\\U+0441\\U+043D\\U+044B\\U+0439")))
(setq $S128 (gip:u "\\U+0414\\U+0438\\U+0444\\U+0444\\U+0435\\U+0440\\U+0435\\U+043D\\U+0446\\U+0438\\U+0430\\U+043B\\U+044C\\U+043D\\U+044B\\U+0439 \\U+0432\\U+044B\\U+043A\\U+043B\\U+044E\\U+0447\\U+0430\\U+0442\\U+0435\\U+043B\\U+044C \\U+0447\\U+0435\\U+0442\\U+044B\\U+0440\\U+0435\\U+0445\\U+043F\\U+043E\\U+043B\\U+044E\\U+0441\\U+043D\\U+044B\\U+0439"))
(setq $S129 (gip:u "\\U+0414\\U+0438\\U+0444\\U+0444\\U+0435\\U+0440\\U+0435\\U+043D\\U+0446\\U+0438\\U+0430\\U+043B\\U+044C\\U+043D\\U+044B\\U+0439 \\U+0432\\U+044B\\U+043A\\U+043B\\U+044E\\U+0447\\U+0430\\U+0442\\U+0435\\U+043B\\U+044C \\U+0434\\U+0432\\U+0443\\U+0445\\U+043F\\U+043E\\U+043B\\U+044E\\U+0441\\U+043D\\U+044B\\U+0439"))
(setq $Q130 (gip:deep-u '(lambda (it)
             (setq it (gip:it-vis it (gip:g o "vis")))
             (gip:it-atts it
               (append
                 (list (cons "\\U+041D\\U+041E\\U+041C.\\U+0422\\U+041E\\U+041A,\\U+0410" (itoa (if (assoc "In" o) (cdr (assoc "In" o)) (gip:g d "In"))))
                       (cons "\\U+041F\\U+0420\\U+041E\\U+0418\\U+0417\\U+0412\\U+041E\\U+0414\\U+0418\\U+0422\\U+0415\\U+041B\\U+042C" (if (assoc "maker" o) (cdr (assoc "maker" o)) (gip:g *gip:b* "name")))
                       (cons "\\U+0421\\U+0415\\U+0420\\U+0418\\U+042F" (gip:gn o "ser" ""))
                       (cons "\\U+041D\\U+041E\\U+041C\\U+0415\\U+0420" (if (assoc "ref" o) (cdr (assoc "ref" o)) (gip:gn d "ref" ""))))
                 (if (gip:g o "ma") (list (cons "I\\U+0421\\U+0420.,\\U+041C\\U+0410" (gip:g o "ma"))))
                 (if (gip:g o "type") (list (cons "\\U+0422\\U+0418\\U+041F" (gip:g o "type")))))))))
(setq $S131 (gip:u "\\U+041B\\U+041E-"))
(setq $S132 (gip:u "\\U+041B\\U+0421-"))
(setq $Q133 (gip:deep-u '("\\U+0410" "A")))
(setq $S134 (gip:u "\\U+041C\\U+0435\\U+0440\\U+043A\\U+0443\\U+0440\\U+0438\\U+0439 236 ART"))
(setq $S135 (gip:u "\\U+041C\\U+0435\\U+0440\\U+043A\\U+0443\\U+0440\\U+0438\\U+0439 204 ARTMX2-02"))
(setq $S136 (gip:u "400/230\\U+0412 5-60\\U+0410"))
(setq $S137 (gip:u "230\\U+0412, 5-100\\U+0410"))
(setq $S138 (gip:u "\\U+0421\\U+0415\\U+0420\\U+0418\\U+042F"))
(setq $S139 (gip:u "\\U+0410"))
(setq $S140 (gip:u "\\U+0410/"))
(setq $S141 (gip:u "\\U+041F\\U+0440\\U+0438\\U+043D\\U+0446\\U+0438\\U+043F\\U+0438\\U+0430\\U+043B\\U+044C\\U+043D\\U+0430\\U+044F \\U+043E\\U+0434\\U+043D\\U+043E\\U+043B\\U+0438\\U+043D\\U+0435\\U+0439\\U+043D\\U+0430\\U+044F \\U+0441\\U+0445\\U+0435\\U+043C\\U+0430 \\U+0449\\U+0438\\U+0442\\U+0430 "))
(setq $S142 (gip:u " \\U+0447."))
(setq $Q143 (gip:deep-u '(lambda (its) (mapcar '(lambda (it) (if (and (= (car it) "E") (= (gip:it-get it 1) "\\U+0429\\U+0420")) (gip:it-set it 1 bname) it)) its))))
(setq $Q144 (gip:deep-u '("type" . "\\U+0410C")))
(setq $Q145 (gip:deep-u '("\\U+0424\\U+0430\\U+0437\\U+0430 A" "\\U+0424\\U+0430\\U+0437\\U+0430 B" "\\U+0424\\U+0430\\U+0437\\U+0430 C")))
(setq $Q146 (gip:deep-u '("P\\U+0443\\U+0441\\U+0442., \\U+043A\\U+0412\\U+0442" . 5)))
(setq $Q147 (gip:deep-u '("P\\U+0440., \\U+043A\\U+0412\\U+0442" . 15)))
(setq $Q148 (gip:deep-u '("I\\U+0440\\U+0430\\U+0441\\U+0447., \\U+0410" . 25)))
(setq $S149 (gip:u "\\U+2014"))
(setq $S150 (gip:u "\\U+041E\\U+0441\\U+043D\\U+043E\\U+0432\\U+043D\\U+044B\\U+0435 \\U+043F\\U+043E\\U+043A\\U+0430\\U+0437\\U+0430\\U+0442\\U+0435\\U+043B\\U+0438 \\U+043F\\U+0440\\U+043E\\U+0435\\U+043A\\U+0442\\U+0430"))
(setq $S151 (gip:u "\\U+041D\\U+0430\\U+043F\\U+0440\\U+044F\\U+0436\\U+0435\\U+043D\\U+0438\\U+0435 \\U+0441\\U+0435\\U+0442\\U+0438, \\U+0412"))
(setq $S152 (gip:u "\\U+0423\\U+0441\\U+0442\\U+0430\\U+043D\\U+043E\\U+0432\\U+043B\\U+0435\\U+043D\\U+043D\\U+0430\\U+044F \\U+043C\\U+043E\\U+0449\\U+043D\\U+043E\\U+0441\\U+0442\\U+044C, \\U+043A\\U+0412\\U+0442"))
(setq $S153 (gip:u "\\U+0420\\U+0430\\U+0441\\U+0447\\U+0435\\U+0442\\U+043D\\U+0430\\U+044F \\U+043C\\U+043E\\U+0449\\U+043D\\U+043E\\U+0441\\U+0442\\U+044C, \\U+043A\\U+0412\\U+0442"))
(setq $S154 (gip:u "\\U+0420\\U+0430\\U+0441\\U+0447\\U+0435\\U+0442\\U+043D\\U+044B\\U+0439 \\U+0442\\U+043E\\U+043A, \\U+0410"))
(setq $S155 (gip:u "\\U+041A\\U+043E\\U+044D\\U+0444\\U+0444\\U+0438\\U+0446\\U+0438\\U+0435\\U+043D\\U+0442 \\U+0441\\U+043F\\U+0440\\U+043E\\U+0441\\U+0430"))
(setq $S156 (gip:u "\\U+0421\\U+0440\\U+0435\\U+0434\\U+043D\\U+0435\\U+0432\\U+0437\\U+0432\\U+0435\\U+0448\\U+0435\\U+043D\\U+043D\\U+044B\\U+0439 cos \\U+03C6"))
(setq $Q157 (gip:deep-u '(lambda (its) (gip:dev-atts its rr (list (cons "ma" (itoa (gip:gn rr "idn" 30))) (cons "ser" (gip:rcd-ser (gip:g *gip:b* (if (= (gip:g rr "w") 4) "rcd4" "rcd2")))) (cons "type" (if (= (gip:g rr "type") "AC") "\\U+0410\\U+0421" "\\U+0410")) (cons "vis" (gip:rcd-vis (= (gip:g rr "w") 4))))))))
(setq $Q158 (gip:deep-u '(lambda (its) (gip:dev-atts its rr (list (cons "ser" (gip:brand-ser *gip:b* tk (gip:g rr "In")))
                                                    (cons "ma" (if isD (itoa (gip:gn rr "idn" 30)))) (cons "type" (if isD "\\U+0410")))))))
(setq $Q159 (gip:deep-u '(lambda (its) (mapcar '(lambda (it) (gip:it-atts it (list (cons "\\U+041F\\U+041E\\U+0417\\U+0418\\U+0426\\U+0418\\U+042F" (gip:g (car rr) "no")) (cons "\\U+0418\\U+041C\\U+042F" (gip:g (cadr rr) "name")) (cons "\\U+041E\\U+041F\\U+0418\\U+0421\\U+0410\\U+041D\\U+0418\\U+0415" (gip:g (cadr rr) "name"))))) its))))
(setq $S160 (gip:u " \\U+043C"))
(setq $S161 (gip:u "\\U+041E\\U+0441\\U+0432\\U+0435\\U+0449\\U+0435\\U+043D\\U+0438\\U+0435 "))
(setq $Q162 (gip:deep-u '(lambda (its) (mapcar '(lambda (it)
                                  (if (and (= (car it) "E") (= (gip:it-get it 0) "MTEXT") (gip:has (gip:gn (cdr it) 1 "") "\\U+041A\\U+043E\\U+0440\\U+043E\\U+0431\\U+043A\\U+0438"))
                                    (progn
                                      (setq it (gip:it-text it "\\U+041A\\U+043E\\U+0440\\U+043E\\U+0431\\U+043A\\U+0438 \\U+0434\\U+043E\\U+043F\\U+043E\\U+043B\\U+043D\\U+0438\\U+0442\\U+0435\\U+043B\\U+044C\\U+043D\\U+043E\\U+0439\n\\U+0441\\U+0438\\U+0441\\U+0442\\U+0435\\U+043C\\U+044B \\U+0443\\U+0440\\U+0430\\U+0432\\U+043D\\U+0438\\U+0432\\U+0430\\U+043D\\U+0438\\U+044F\n\\U+043F\\U+043E\\U+0442\\U+0435\\U+043D\\U+0446\\U+0438\\U+0430\\U+043B\\U+043E\\U+0432"))
                                      (setq it (gip:it-set it 41 2493.87862559041))
                                      (cons "E" (subst (list 10 (- AXk 300.0) (- OY 7022.0) 0.0) (assoc 10 (cdr it)) (cdr it))))
                                    it)) its))))
(setq $S163 (gip:u "GIP_\\U+041C\\U+043E\\U+043D\\U+0442\\U+0430\\U+0436"))
(setq $S164 (gip:u "\\U+2026"))
(setq $S165 (gip:u "\\U+041E\\U+0441\\U+0432\\U+0435\\U+0449. "))
(setq $S166 (gip:u "\\U+0417\\U+0430\\U+0449\\U+0438\\U+0442\\U+0430 \\U+043A\\U+0430\\U+0442\\U+0443\\U+0448\\U+043A\\U+0438 KM1"))
(setq $S167 (gip:u "\\U+0412\\U+0432\\U+043E\\U+0434\\U+043D\\U+043E\\U+0439 \\U+0430\\U+0432\\U+0442\\U+043E\\U+043C\\U+0430\\U+0442"))
(setq $S168 (gip:u "\\U+0420\\U+0435\\U+043B\\U+0435 \\U+043D\\U+0430\\U+043F\\U+0440\\U+044F\\U+0436\\U+0435\\U+043D\\U+0438\\U+044F"))
(setq $S169 (gip:u "\\U+0423\\U+0417\\U+041E \\U+043F\\U+0440\\U+043E\\U+0442\\U+0438\\U+0432\\U+043E\\U+043F\\U+043E\\U+0436\\U+0430\\U+0440\\U+043D\\U+043E\\U+0435"))
(setq $S170 (gip:u "\\U+041A\\U+043E\\U+043D\\U+0442\\U+0430\\U+043A\\U+0442\\U+043E\\U+0440"))
(setq $S171 (gip:u "\\U+0423\\U+0417\\U+041E \\U+0433\\U+0440. "))
(setq $S172 (gip:u " \\U+041A\\U+0440\\U+043E\\U+0441\\U+0441-\\U+043C\\U+043E\\U+0434\\U+0443\\U+043B\\U+044C"))
(setq $S173 (gip:u "\nGIP: \\U+043D\\U+0435\\U+0442 \\U+0431\\U+043B\\U+043E\\U+043A\\U+0430 "))
(setq $S174 (gip:u "N \\U+043E\\U+0431\\U+0449\\U+0438\\U+0439"))
(setq $S175 (gip:u "\\U+0428\\U+0438\\U+043D\\U+0430 \\U+0437\\U+0430\\U+0437\\U+0435\\U+043C\\U+043B\\U+0435\\U+043D\\U+0438\\U+044F"))
(setq $S176 (gip:u "3\\U+0424+N"))
(setq $S177 (gip:u "3\\U+0424"))
(setq $S178 (gip:u "\\U+0412\\U+0432\\U+043E\\U+0434 3\\U+0424+N"))
(setq $S179 (gip:u "\\U+0412\\U+0432\\U+043E\\U+0434 1\\U+0424+N"))
(setq $S180 (gip:u "\\U+041A\\U+043B\\U+0430\\U+0432\\U+0438\\U+0448\\U+0430 \\U+00AB\\U+041C\\U+0430\\U+0441\\U+0442\\U+0435\\U+0440 \\U+0432\\U+044B\\U+043A\\U+043B\\U+00BB"))
(setq $S181 (gip:u "\\U+0429\\U+0438\\U+0442 \\U+0440\\U+0430\\U+0441\\U+043F\\U+0440\\U+0435\\U+0434\\U+0435\\U+043B\\U+0438\\U+0442\\U+0435\\U+043B\\U+044C\\U+043D\\U+044B\\U+0439 \\U+0432\\U+0441\\U+0442\\U+0440\\U+0430\\U+0438\\U+0432\\U+0430\\U+0435\\U+043C\\U+044B\\U+0439 "))
(setq $S182 (gip:u "\\U+0440\\U+044F\\U+0434"))
(setq $S183 (gip:u "\\U+0440\\U+044F\\U+0434\\U+0430"))
(setq $S184 (gip:u "\\U+0440\\U+044F\\U+0434\\U+043E\\U+0432"))
(setq $S185 (gip:u " \\U+043C\\U+043E\\U+0434., "))
(setq $S186 (gip:u ", \\U+0441 \\U+043A\\U+043B\\U+0435\\U+043C\\U+043C\\U+043D\\U+0438\\U+043A\\U+0430\\U+043C\\U+0438 N/PE"))
(setq $S187 (gip:u "\\U+0448\\U+0442."))
(setq $S188 (gip:u "\\U+0429\\U+0438\\U+0442 \\U+0440\\U+0430\\U+0441\\U+043F\\U+0440\\U+0435\\U+0434\\U+0435\\U+043B\\U+0438\\U+0442\\U+0435\\U+043B\\U+044C\\U+043D\\U+044B\\U+0439 \\U+0432\\U+0441\\U+0442\\U+0440\\U+0430\\U+0438\\U+0432\\U+0430\\U+0435\\U+043C\\U+044B\\U+0439 \\U+0441 \\U+043A\\U+043B\\U+0435\\U+043C\\U+043C\\U+043D\\U+0438\\U+043A\\U+0430\\U+043C\\U+0438 N/PE, IP41, "))
(setq $S189 (gip:u " \\U+043C\\U+043E\\U+0434."))
(setq $S190 (gip:u "\\U+0420\\U+0435\\U+043B\\U+0435 \\U+043A\\U+043E\\U+043D\\U+0442\\U+0440\\U+043E\\U+043B\\U+044F \\U+043D\\U+0430\\U+043F\\U+0440\\U+044F\\U+0436\\U+0435\\U+043D\\U+0438\\U+044F, 1-\\U+043F\\U+043E\\U+043B\\U+044E\\U+0441\\U+043D\\U+043E\\U+0435, 63\\U+0410"))
(setq $S191 (gip:u "\\U+0412\\U+044B\\U+043A\\U+043B\\U+044E\\U+0447\\U+0430\\U+0442\\U+0435\\U+043B\\U+044C \\U+0430\\U+0432\\U+0442\\U+043E\\U+043C\\U+0430\\U+0442\\U+0438\\U+0447\\U+0435\\U+0441\\U+043A\\U+0438\\U+0439, "))
(setq $S192 (gip:u "-\\U+043F\\U+043E\\U+043B\\U+044E\\U+0441\\U+043D\\U+044B\\U+0439, "))
(setq $S193 (gip:u "A, \\U+0445\\U+0430\\U+0440-\\U+043A\\U+0430 \\U+00ABC\\U+00BB"))
(setq $S194 (gip:u "\\U+0412\\U+044B\\U+043A\\U+043B\\U+044E\\U+0447\\U+0430\\U+0442\\U+0435\\U+043B\\U+044C \\U+0434\\U+0438\\U+0444\\U+0444\\U+0435\\U+0440\\U+0435\\U+043D\\U+0446\\U+0438\\U+0430\\U+043B\\U+044C\\U+043D\\U+044B\\U+0439, "))
(setq $S195 (gip:u "A, \\U+0445\\U+0430\\U+0440-\\U+043A\\U+0430 \\U+00ABC\\U+00BB, "))
(setq $S196 (gip:u "\\U+043C\\U+0410, \\U+0442\\U+0438\\U+043F \\U+00ABA\\U+00BB"))
(setq $S197 (gip:u "\\U+0423\\U+0441\\U+0442\\U+0440\\U+043E\\U+0439\\U+0441\\U+0442\\U+0432\\U+043E \\U+0437\\U+0430\\U+0449\\U+0438\\U+0442\\U+043D\\U+043E\\U+0433\\U+043E \\U+043E\\U+0442\\U+043A\\U+043B\\U+044E\\U+0447\\U+0435\\U+043D\\U+0438\\U+044F, "))
(setq $S198 (gip:u "-\\U+043F\\U+043E\\U+043B\\U+044E\\U+0441\\U+043D\\U+043E\\U+0435, "))
(setq $S199 (gip:u "\\U+043C\\U+0410, \\U+0442\\U+0438\\U+043F \\U+00AB"))
(setq $S200 (gip:u "\\U+00BB"))
(setq $S201 (gip:u "\\U+0423\\U+0441\\U+0442\\U+0440\\U+043E\\U+0439\\U+0441\\U+0442\\U+0432\\U+043E \\U+0437\\U+0430\\U+0449\\U+0438\\U+0442\\U+043D\\U+043E\\U+0433\\U+043E \\U+043E\\U+0442\\U+043A\\U+043B\\U+044E\\U+0447\\U+0435\\U+043D\\U+0438\\U+044F \\U+043F\\U+0440\\U+043E\\U+0442\\U+0438\\U+0432\\U+043E\\U+043F\\U+043E\\U+0436\\U+0430\\U+0440\\U+043D\\U+043E\\U+0435, "))
(setq $S202 (gip:u "A, 100\\U+043C\\U+0410, \\U+0442\\U+0438\\U+043F \\U+00ABAC\\U+00BB"))
(setq $S203 (gip:u "\\U+041A\\U+043E\\U+043D\\U+0442\\U+0430\\U+043A\\U+0442\\U+043E\\U+0440 \\U+043C\\U+043E\\U+0434\\U+0443\\U+043B\\U+044C\\U+043D\\U+044B\\U+0439 \\U+0441 \\U+043A\\U+0430\\U+0442\\U+0443\\U+0448\\U+043A\\U+043E\\U+0439 \\U+0443\\U+043F\\U+0440. 230\\U+0412, "))
(setq $S204 (gip:u "\\U+041D\\U+041E"))
(setq $S205 (gip:u "\\U+0420\\U+0430\\U+0441\\U+043F\\U+0440\\U+0435\\U+0434\\U+0435\\U+043B\\U+0438\\U+0442\\U+0435\\U+043B\\U+044C\\U+043D\\U+044B\\U+0439 \\U+0431\\U+043B\\U+043E\\U+043A (\\U+043A\\U+0440\\U+043E\\U+0441\\U+0441-\\U+043C\\U+043E\\U+0434\\U+0443\\U+043B\\U+044C) "))
(setq $S206 (gip:u "4\\U+041F"))
(setq $S207 (gip:u "2\\U+041F"))
(setq $S208 (gip:u "\\U+0428\\U+0438\\U+043D\\U+0430 \\U+043D\\U+0443\\U+043B\\U+0435\\U+0432\\U+0430\\U+044F N \\U+043D\\U+0430 \\U+0438\\U+0437\\U+043E\\U+043B\\U+044F\\U+0442\\U+043E\\U+0440\\U+0430\\U+0445"))
(setq $S209 (gip:u "\\U+0428\\U+0438\\U+043D\\U+0430 \\U+0437\\U+0430\\U+0449\\U+0438\\U+0442\\U+043D\\U+0430\\U+044F PE \\U+043D\\U+0430 \\U+0438\\U+0437\\U+043E\\U+043B\\U+044F\\U+0442\\U+043E\\U+0440\\U+0430\\U+0445"))
(setq $Q210 (gip:deep-u '(
  ("\\U+0421\\U+0432\\U+0435\\U+0442\\U+0438\\U+043B\\U+044C\\U+043D\\U+0438\\U+043A \\U+043F\\U+043E\\U+0442\\U+043E\\U+043B\\U+043E\\U+0447\\U+043D\\U+044B\\U+0439" "\\U+0421\\U+0432\\U+0435\\U+0442\\U+0438\\U+043B\\U+044C\\U+043D\\U+0438\\U+043A \\U+043F\\U+043E\\U+0442\\U+043E\\U+043B\\U+043E\\U+0447\\U+043D\\U+044B\\U+0439, IP20" "c")
  ("\\U+0421\\U+0432\\U+0435\\U+0442\\U+0438\\U+043B\\U+044C\\U+043D\\U+0438\\U+043A \\U+043F\\U+043E\\U+0434\\U+0432\\U+0435\\U+0441\\U+043D\\U+043E\\U+0439" "\\U+041F\\U+043E\\U+0434\\U+0432\\U+0435\\U+0441\\U+043D\\U+043E\\U+0439 \\U+0441\\U+0432\\U+0435\\U+0442\\U+0438\\U+043B\\U+044C\\U+043D\\U+0438\\U+043A, IP20" "c")
  ("\\U+0421\\U+0432\\U+0435\\U+0442\\U+0438\\U+043B\\U+044C\\U+043D\\U+0438\\U+043A \\U+043D\\U+0430\\U+0441\\U+0442\\U+043E\\U+043B\\U+044C\\U+043D\\U+044B\\U+0439 / \\U+043D\\U+0430\\U+043F\\U+043E\\U+043B\\U+044C\\U+043D\\U+044B\\U+0439" "\\U+0421\\U+0432\\U+0435\\U+0442\\U+0438\\U+043B\\U+044C\\U+043D\\U+0438\\U+043A \\U+043D\\U+0430\\U+0441\\U+0442\\U+043E\\U+043B\\U+044C\\U+043D\\U+044B\\U+0439/\\U+043D\\U+0430\\U+043F\\U+043E\\U+043B\\U+044C\\U+043D\\U+044B\\U+0439, IP20" "c")
  ("\\U+0421\\U+0432\\U+0435\\U+0442\\U+0438\\U+043B\\U+044C\\U+043D\\U+0438\\U+043A \\U+0432\\U+0441\\U+0442\\U+0440\\U+0430\\U+0438\\U+0432\\U+0430\\U+0435\\U+043C\\U+044B\\U+0439" "\\U+0421\\U+0432\\U+0435\\U+0442\\U+0438\\U+043B\\U+044C\\U+043D\\U+0438\\U+043A \\U+0432\\U+0441\\U+0442\\U+0440\\U+0430\\U+0438\\U+0432\\U+0430\\U+0435\\U+043C\\U+044B\\U+0439, IP20" "c")
  ("\\U+0421\\U+0432\\U+0435\\U+0442\\U+0438\\U+043B\\U+044C\\U+043D\\U+0438\\U+043A \\U+043D\\U+0430\\U+043A\\U+043B\\U+0430\\U+0434\\U+043D\\U+043E\\U+0439" "\\U+0421\\U+0432\\U+0435\\U+0442\\U+0438\\U+043B\\U+044C\\U+043D\\U+0438\\U+043A \\U+043D\\U+0430\\U+043A\\U+043B\\U+0430\\U+0434\\U+043D\\U+043E\\U+0439, IP20" "c")
  ("\\U+0421\\U+0432\\U+0435\\U+0442\\U+0438\\U+043B\\U+044C\\U+043D\\U+0438\\U+043A \\U+043D\\U+0430\\U+0441\\U+0442\\U+0435\\U+043D\\U+043D\\U+044B\\U+0439" "\\U+0421\\U+0432\\U+0435\\U+0442\\U+0438\\U+043B\\U+044C\\U+043D\\U+0438\\U+043A \\U+043D\\U+0430\\U+0441\\U+0442\\U+0435\\U+043D\\U+043D\\U+044B\\U+0439, IP20" "c")
  ("\\U+0421\\U+0432\\U+0435\\U+0442\\U+0438\\U+043B\\U+044C\\U+043D\\U+0438\\U+043A \\U+0442\\U+0440\\U+0435\\U+043A\\U+043E\\U+0432\\U+044B\\U+0439" "\\U+0421\\U+0432\\U+0435\\U+0442\\U+0438\\U+043B\\U+044C\\U+043D\\U+0438\\U+043A \\U+0442\\U+0440\\U+0435\\U+043A\\U+043E\\U+0432\\U+044B\\U+0439, IP20" "c")
  ("\\U+0421\\U+0432\\U+0435\\U+0442\\U+0438\\U+043B\\U+044C\\U+043D\\U+0438\\U+043A \\U+043F\\U+043E\\U+0442\\U+043E\\U+043B\\U+043E\\U+0447\\U+043D\\U+044B\\U+0439 IP44" "\\U+0421\\U+0432\\U+0435\\U+0442\\U+0438\\U+043B\\U+044C\\U+043D\\U+0438\\U+043A \\U+043F\\U+043E\\U+0442\\U+043E\\U+043B\\U+043E\\U+0447\\U+043D\\U+044B\\U+0439, IP44" "c")
  ("\\U+0421\\U+0432\\U+0435\\U+0442\\U+0438\\U+043B\\U+044C\\U+043D\\U+0438\\U+043A \\U+0432\\U+0441\\U+0442\\U+0440\\U+0430\\U+0438\\U+0432\\U+0430\\U+0435\\U+043C\\U+044B\\U+0439 IP44" "\\U+0421\\U+0432\\U+0435\\U+0442\\U+0438\\U+043B\\U+044C\\U+043D\\U+0438\\U+043A \\U+0432\\U+0441\\U+0442\\U+0440\\U+0430\\U+0438\\U+0432\\U+0430\\U+0435\\U+043C\\U+044B\\U+0439, IP44" "c")
  ("\\U+0421\\U+0432\\U+0435\\U+0442\\U+0438\\U+043B\\U+044C\\U+043D\\U+0438\\U+043A \\U+043D\\U+0430\\U+043A\\U+043B\\U+0430\\U+0434\\U+043D\\U+043E\\U+0439 IP44" "\\U+0421\\U+0432\\U+0435\\U+0442\\U+0438\\U+043B\\U+044C\\U+043D\\U+0438\\U+043A \\U+043D\\U+0430\\U+043A\\U+043B\\U+0430\\U+0434\\U+043D\\U+043E\\U+0439, IP44" "c")
  ("\\U+0421\\U+0432\\U+0435\\U+0442\\U+0438\\U+043B\\U+044C\\U+043D\\U+0438\\U+043A \\U+043D\\U+0430\\U+0441\\U+0442\\U+0435\\U+043D\\U+043D\\U+044B\\U+0439 IP44" "\\U+0421\\U+0432\\U+0435\\U+0442\\U+0438\\U+043B\\U+044C\\U+043D\\U+0438\\U+043A \\U+043D\\U+0430\\U+0441\\U+0442\\U+0435\\U+043D\\U+043D\\U+044B\\U+0439, IP44" "c")
  ("\\U+0421\\U+0432\\U+0435\\U+0442\\U+0438\\U+043B\\U+044C\\U+043D\\U+0438\\U+043A \\U+0442\\U+0440\\U+0435\\U+043A\\U+043E\\U+0432\\U+044B\\U+0439 IP44" "\\U+0421\\U+0432\\U+0435\\U+0442\\U+0438\\U+043B\\U+044C\\U+043D\\U+0438\\U+043A \\U+0442\\U+0440\\U+0435\\U+043A\\U+043E\\U+0432\\U+044B\\U+0439, IP44" "c")
  ("\\U+0412\\U+044B\\U+043A\\U+043B\\U+044E\\U+0447\\U+0430\\U+0442\\U+0435\\U+043B\\U+044C 1 \\U+043A\\U+043B\\U+0430\\U+0432\\U+0438\\U+0448\\U+043D\\U+044B\\U+0439, 1\\U+043F, 16\\U+0410" "\\U+041C\\U+0435\\U+0445\\U+0430\\U+043D\\U+0438\\U+0437\\U+043C \\U+0432\\U+044B\\U+043A\\U+043B\\U+044E\\U+0447\\U+0430\\U+0442\\U+0435\\U+043B\\U+044F \\U+043E\\U+0434\\U+043D\\U+043E\\U+043A\\U+043B\\U+0430\\U+0432\\U+0438\\U+0448\\U+043D\\U+043E\\U+0433\\U+043E \\U+0441\\U+043A\\U+0440\\U+044B\\U+0442\\U+043E\\U+0439 \\U+043F\\U+0440\\U+043E\\U+0432\\U+043E\\U+0434\\U+043A\\U+0438, IP20" "s")
  ("\\U+0412\\U+044B\\U+043A\\U+043B\\U+044E\\U+0447\\U+0430\\U+0442\\U+0435\\U+043B\\U+044C 2 \\U+043A\\U+043B\\U+0430\\U+0432\\U+0438\\U+0448\\U+043D\\U+044B\\U+0439, 1\\U+043F, 16A" "\\U+041C\\U+0435\\U+0445\\U+0430\\U+043D\\U+0438\\U+0437\\U+043C \\U+0432\\U+044B\\U+043A\\U+043B\\U+044E\\U+0447\\U+0430\\U+0442\\U+0435\\U+043B\\U+044F \\U+0434\\U+0432\\U+0443\\U+0445\\U+043A\\U+043B\\U+0430\\U+0432\\U+0438\\U+0448\\U+043D\\U+043E\\U+0433\\U+043E \\U+0441\\U+043A\\U+0440\\U+044B\\U+0442\\U+043E\\U+0439 \\U+043F\\U+0440\\U+043E\\U+0432\\U+043E\\U+0434\\U+043A\\U+0438, IP20" "s")
  ("\\U+0412\\U+044B\\U+043A\\U+043B\\U+044E\\U+0447\\U+0430\\U+0442\\U+0435\\U+043B\\U+044C 3 \\U+043A\\U+043B\\U+0430\\U+0432\\U+0438\\U+0448\\U+043D\\U+044B\\U+0439, 1\\U+043F, 16A" "\\U+041C\\U+0435\\U+0445\\U+0430\\U+043D\\U+0438\\U+0437\\U+043C \\U+0432\\U+044B\\U+043A\\U+043B\\U+044E\\U+0447\\U+0430\\U+0442\\U+0435\\U+043B\\U+044F \\U+0442\\U+0440\\U+0451\\U+0445\\U+043A\\U+043B\\U+0430\\U+0432\\U+0438\\U+0448\\U+043D\\U+043E\\U+0433\\U+043E \\U+0441\\U+043A\\U+0440\\U+044B\\U+0442\\U+043E\\U+0439 \\U+043F\\U+0440\\U+043E\\U+0432\\U+043E\\U+0434\\U+043A\\U+0438, IP20" "s")
  ("\\U+041F\\U+0435\\U+0440\\U+0435\\U+043A\\U+043B\\U+044E\\U+0447\\U+0430\\U+0442\\U+0435\\U+043B\\U+044C 1 \\U+043A\\U+043B\\U+0430\\U+0432\\U+0438\\U+0448\\U+043D\\U+044B\\U+0439, 1\\U+043F, 16A" "\\U+041C\\U+0435\\U+0445\\U+0430\\U+043D\\U+0438\\U+0437\\U+043C \\U+043F\\U+0435\\U+0440\\U+0435\\U+043A\\U+043B\\U+044E\\U+0447\\U+0430\\U+0442\\U+0435\\U+043B\\U+044F \\U+043E\\U+0434\\U+043D\\U+043E\\U+043A\\U+043B\\U+0430\\U+0432\\U+0438\\U+0448\\U+043D\\U+043E\\U+0433\\U+043E \\U+0441\\U+043A\\U+0440\\U+044B\\U+0442\\U+043E\\U+0439 \\U+043F\\U+0440\\U+043E\\U+0432\\U+043E\\U+0434\\U+043A\\U+0438, IP20" "s")
  ("\\U+041F\\U+0435\\U+0440\\U+0435\\U+043A\\U+043B\\U+044E\\U+0447\\U+0430\\U+0442\\U+0435\\U+043B\\U+044C 2 \\U+043A\\U+043B\\U+0430\\U+0432\\U+0438\\U+0448\\U+043D\\U+044B\\U+0439, 1\\U+043F, 16A" "\\U+041C\\U+0435\\U+0445\\U+0430\\U+043D\\U+0438\\U+0437\\U+043C \\U+043F\\U+0435\\U+0440\\U+0435\\U+043A\\U+043B\\U+044E\\U+0447\\U+0430\\U+0442\\U+0435\\U+043B\\U+044F \\U+0434\\U+0432\\U+0443\\U+0445\\U+043A\\U+043B\\U+0430\\U+0432\\U+0438\\U+0448\\U+043D\\U+043E\\U+0433\\U+043E \\U+0441\\U+043A\\U+0440\\U+044B\\U+0442\\U+043E\\U+0439 \\U+043F\\U+0440\\U+043E\\U+0432\\U+043E\\U+0434\\U+043A\\U+0438, IP20" "s")
  ("\\U+0414\\U+0438\\U+043C\\U+043C\\U+0435\\U+0440" "\\U+041C\\U+0435\\U+0445\\U+0430\\U+043D\\U+0438\\U+0437\\U+043C \\U+0441\\U+0432\\U+0435\\U+0442\\U+043E\\U+0440\\U+0435\\U+0433\\U+0443\\U+043B\\U+044F\\U+0442\\U+043E\\U+0440\\U+0430 (\\U+0434\\U+0438\\U+043C\\U+043C\\U+0435\\U+0440\\U+0430) \\U+0441\\U+043A\\U+0440\\U+044B\\U+0442\\U+043E\\U+0439 \\U+043F\\U+0440\\U+043E\\U+0432\\U+043E\\U+0434\\U+043A\\U+0438, IP20" "s")
  ("\\U+0414\\U+0430\\U+0442\\U+0447\\U+0438\\U+043A \\U+0434\\U+0432\\U+0438\\U+0436\\U+0435\\U+043D\\U+0438\\U+044F" "\\U+0414\\U+0430\\U+0442\\U+0447\\U+0438\\U+043A \\U+0434\\U+0432\\U+0438\\U+0436\\U+0435\\U+043D\\U+0438\\U+044F, IP20" "s")
  ("\\U+0420\\U+043E\\U+0437\\U+0435\\U+0442\\U+043A\\U+0430 \\U+0448\\U+0442\\U+0435\\U+043F\\U+0441\\U+0435\\U+043B\\U+044C\\U+043D\\U+0430\\U+044F \\U+0441\\U+0438\\U+043B\\U+043E\\U+0432\\U+0430\\U+044F, 16A, L+N+PE (1\\U+0424)" "\\U+041E\\U+0434\\U+043D\\U+043E\\U+0444\\U+0430\\U+0437\\U+043D\\U+0430\\U+044F \\U+0440\\U+043E\\U+0437\\U+0435\\U+0442\\U+043A\\U+0430 \\U+0441 \\U+0437\\U+0430\\U+0437\\U+0435\\U+043C\\U+043B\\U+044F\\U+044E\\U+0449\\U+0438\\U+043C \\U+043A\\U+043E\\U+043D\\U+0442\\U+0430\\U+043A\\U+0442\\U+043E\\U+043C IP20" "s")
  ("\\U+0420\\U+043E\\U+0437\\U+0435\\U+0442\\U+043A\\U+0430 \\U+0448\\U+0442\\U+0435\\U+043F\\U+0441\\U+0435\\U+043B\\U+044C\\U+043D\\U+0430\\U+044F \\U+0441\\U+0438\\U+043B\\U+043E\\U+0432\\U+0430\\U+044F, 16A, L+N+PE (1\\U+0424) IP44" "\\U+041E\\U+0434\\U+043D\\U+043E\\U+0444\\U+0430\\U+0437\\U+043D\\U+0430\\U+044F \\U+0440\\U+043E\\U+0437\\U+0435\\U+0442\\U+043A\\U+0430 \\U+0441 \\U+0437\\U+0430\\U+0437\\U+0435\\U+043C\\U+043B\\U+044F\\U+044E\\U+0449\\U+0438\\U+043C \\U+043A\\U+043E\\U+043D\\U+0442\\U+0430\\U+043A\\U+0442\\U+043E\\U+043C IP44" "s")
  ("\\U+0420\\U+043E\\U+0437\\U+0435\\U+0442\\U+043A\\U+0430 \\U+0448\\U+0442\\U+0435\\U+043F\\U+0441\\U+0435\\U+043B\\U+044C\\U+043D\\U+0430\\U+044F \\U+0441\\U+0438\\U+043B\\U+043E\\U+0432\\U+0430\\U+044F, 16A, 3L+N+PE (3\\U+0424)" "\\U+0422\\U+0440\\U+0451\\U+0445\\U+0444\\U+0430\\U+0437\\U+043D\\U+0430\\U+044F \\U+0440\\U+043E\\U+0437\\U+0435\\U+0442\\U+043A\\U+0430 \\U+0441 \\U+0437\\U+0430\\U+0437\\U+0435\\U+043C\\U+043B\\U+044F\\U+044E\\U+0449\\U+0438\\U+043C \\U+043A\\U+043E\\U+043D\\U+0442\\U+0430\\U+043A\\U+0442\\U+043E\\U+043C" "s")
  ("\\U+0420\\U+043E\\U+0437\\U+0435\\U+0442\\U+043A\\U+0430 USB, IP20" "\\U+0420\\U+043E\\U+0437\\U+0435\\U+0442\\U+043A\\U+0430 USB, IP20" "s")
  ("\\U+0422\\U+0435\\U+0440\\U+043C\\U+043E\\U+0440\\U+0435\\U+0433\\U+0443\\U+043B\\U+044F\\U+0442\\U+043E\\U+0440 \\U+0422\\U+041F" "\\U+0422\\U+0435\\U+0440\\U+043C\\U+043E\\U+0440\\U+0435\\U+0433\\U+0443\\U+043B\\U+044F\\U+0442\\U+043E\\U+0440 \\U+0442\\U+0451\\U+043F\\U+043B\\U+043E\\U+0433\\U+043E \\U+043F\\U+043E\\U+043B\\U+0430" "s")
  ("\\U+041B\\U+044E\\U+0447\\U+043E\\U+043A \\U+0432\\U+043D\\U+0443\\U+0442\\U+0440\\U+0438\\U+043F\\U+043E\\U+043B\\U+044C\\U+043D\\U+044B\\U+0439 \\U+0440\\U+043E\\U+0437\\U+0435\\U+0442\\U+043E\\U+0447\\U+043D\\U+044B\\U+0439 1 \\U+0440\\U+043E\\U+0437., 16A, L+N+PE, IP44" "\\U+041B\\U+044E\\U+0447\\U+043E\\U+043A \\U+0432\\U+043D\\U+0443\\U+0442\\U+0440\\U+0438\\U+043F\\U+043E\\U+043B\\U+044C\\U+043D\\U+044B\\U+0439 \\U+0440\\U+043E\\U+0437\\U+0435\\U+0442\\U+043E\\U+0447\\U+043D\\U+044B\\U+0439 1 \\U+0440\\U+043E\\U+0437., 16A, IP44" "s")
  ("\\U+041B\\U+044E\\U+0447\\U+043E\\U+043A \\U+0432\\U+043D\\U+0443\\U+0442\\U+0440\\U+0438\\U+043F\\U+043E\\U+043B\\U+044C\\U+043D\\U+044B\\U+0439 \\U+0440\\U+043E\\U+0437\\U+0435\\U+0442\\U+043E\\U+0447\\U+043D\\U+044B\\U+0439 2 \\U+0440\\U+043E\\U+0437., 16A, L+N+PE, IP44" "\\U+041B\\U+044E\\U+0447\\U+043E\\U+043A \\U+0432\\U+043D\\U+0443\\U+0442\\U+0440\\U+0438\\U+043F\\U+043E\\U+043B\\U+044C\\U+043D\\U+044B\\U+0439 \\U+0440\\U+043E\\U+0437\\U+0435\\U+0442\\U+043E\\U+0447\\U+043D\\U+044B\\U+0439 2 \\U+0440\\U+043E\\U+0437., 16A, IP44" "s"))))
(setq $Q211 (gip:deep-u '("\\U+042D\\U+041E\\U+041C_\\U+0420\\U+043E\\U+0437\\U+0435\\U+0442\\U+043A\\U+0438_GIP" "\\U+042D\\U+041E\\U+041C_\\U+0412\\U+044B\\U+043A\\U+043B\\U+044E\\U+0447\\U+0430\\U+0442\\U+0435\\U+043B\\U+0438_GIP" "\\U+042D\\U+041E\\U+041C_\\U+0421\\U+0432\\U+0435\\U+0442\\U+0438\\U+043B\\U+044C\\U+043D\\U+0438\\U+043A\\U+0438_GIP")))
(setq $S212 (gip:u "\\U+043E\\U+043F\\U+0440\\U+0435\\U+0434\\U+0435\\U+043B\\U+044F\\U+0435\\U+0442\\U+0441\\U+044F \\U+0437\\U+0430\\U+043A\\U+0430\\U+0437\\U+0447\\U+0438\\U+043A\\U+043E\\U+043C"))
(setq $S213 (gip:u "\\U+041C\\U+043E\\U+043D\\U+0442\\U+0430\\U+0436\\U+043D\\U+0430\\U+044F \\U+043A\\U+043E\\U+0440\\U+043E\\U+0431\\U+043A\\U+0430 \\U+043D\\U+0430 1 \\U+043F\\U+043E\\U+0441\\U+0442 \\U+0434\\U+043B\\U+044F \\U+0441\\U+0443\\U+0445\\U+0438\\U+0445 \\U+043F\\U+0435\\U+0440\\U+0435\\U+0433\\U+043E\\U+0440\\U+043E\\U+0434\\U+043E\\U+043A, \\U+0433\\U+043B\\U+0443\\U+0431. 50 \\U+043C\\U+043C"))
(setq $S214 (gip:u "\\U+0445"))
(setq $S215 (gip:u "\\U+041A\\U+043B\\U+0438\\U+043F\\U+0441\\U+0430 \\U+0434\\U+043B\\U+044F \\U+0442\\U+0440\\U+0443\\U+0431\\U+043A\\U+0438 d="))
(setq $S216 (gip:u "\\U+043C\\U+043C"))
(setq $S217 (gip:u "\\U+041F\\U+0440\\U+043E\\U+043C\\U+0440\\U+0443\\U+043A\\U+0430\\U+0432"))
(setq $S218 (gip:u "\\U+0422\\U+0440\\U+0443\\U+0431\\U+0430 \\U+0433\\U+043E\\U+0444\\U+0440\\U+0438\\U+0440\\U+043E\\U+0432\\U+0430\\U+043D\\U+043D\\U+0430\\U+044F d="))
(setq $S219 (gip:u "\\U+043F.\\U+043C."))
(setq $S220 (gip:u "\\U+0420\\U+0430\\U+0441\\U+0445\\U+043E\\U+0434\\U+043D\\U+044B\\U+0435 \\U+043C\\U+0430\\U+0442\\U+0435\\U+0440\\U+0438\\U+0430\\U+043B\\U+044B"))
(setq $S221 (gip:u "\\U+043A\\U+043E\\U+043C\\U+043F\\U+043B."))
(setq $S222 (gip:u "\\U+041A\\U+043E\\U+043C\\U+043F\\U+043B\\U+0435\\U+043A\\U+0442 \\U+0442\\U+0451\\U+043F\\U+043B\\U+043E\\U+0433\\U+043E \\U+043F\\U+043E\\U+043B\\U+0430"))
(setq $S223 (gip:u "\\U+041A\\U+043E\\U+0440\\U+043E\\U+0431\\U+043A\\U+0430 \\U+0443\\U+0440\\U+0430\\U+0432\\U+043D\\U+0438\\U+0432\\U+0430\\U+043D\\U+0438\\U+044F \\U+043F\\U+043E\\U+0442\\U+0435\\U+043D\\U+0446\\U+0438\\U+0430\\U+043B\\U+043E\\U+0432 \\U+0434\\U+043B\\U+044F \\U+0431\\U+0435\\U+0442\\U+043E\\U+043D\\U+0430, 32\\U+0410"))
(setq $S224 (gip:u "\\U+041C\\U+041F\\U+041E \\U+042D\\U+043B\\U+0435\\U+043A\\U+0442\\U+0440\\U+043E\\U+043C\\U+043E\\U+043D\\U+0442\\U+0430\\U+0436"))
(setq $S225 (gip:u "\\U+041A\\U+0430\\U+0431\\U+0435\\U+043B\\U+044C \\U+0441\\U+0438\\U+043B\\U+043E\\U+0432\\U+043E\\U+0439, "))
(setq $S226 (gip:u "\\U+043A\\U+0432.\\U+043C\\U+043C"))
(setq $S227 (gip:u "\\U+041A\\U+043E\\U+043D\\U+043A\\U+043E\\U+0440\\U+0434"))
(setq $S228 (gip:u "\\U+041F\\U+0440\\U+043E\\U+0432\\U+043E\\U+0434 \\U+0436\\U+0435\\U+043B\\U+0442\\U+043E-\\U+0437\\U+0435\\U+043B\\U+0451\\U+043D\\U+044B\\U+0439, 1\\U+04456\\U+043A\\U+0432.\\U+043C\\U+043C"))
(setq $S229 (gip:u "\\U+041F\\U+0443\\U+0413\\U+0412\\U+043D\\U+0433(\\U+0410)-LS"))
(setq $S230 (gip:u "\\U+041F\\U+0440\\U+043E\\U+0432\\U+043E\\U+0434 \\U+0436\\U+0435\\U+043B\\U+0442\\U+043E-\\U+0437\\U+0435\\U+043B\\U+0451\\U+043D\\U+044B\\U+0439, 1\\U+04452,5\\U+043A\\U+0432.\\U+043C\\U+043C"))
(setq $S231 (gip:u "\\U+0429\\U+0438\\U+0442\\U+043E\\U+0432\\U+043E\\U+0435 \\U+043E\\U+0431\\U+043E\\U+0440\\U+0443\\U+0434\\U+043E\\U+0432\\U+0430\\U+043D\\U+0438\\U+0435"))
(setq $S232 (gip:u "\\U+041E\\U+0431\\U+043E\\U+0440\\U+0443\\U+0434\\U+043E\\U+0432\\U+0430\\U+043D\\U+0438\\U+0435"))
(setq $S233 (gip:u "\\U+041C\\U+0430\\U+0442\\U+0435\\U+0440\\U+0438\\U+0430\\U+043B\\U+044B"))
(setq $S234 (gip:u "\\U+041A\\U+0430\\U+0431\\U+0435\\U+043B\\U+044C\\U+043D\\U+0430\\U+044F \\U+043F\\U+0440\\U+043E\\U+0434\\U+0443\\U+043A\\U+0446\\U+0438\\U+044F"))
(setq $Q235 (gip:deep-u '(lambda (its) (mapcar '(lambda (it) (if (= (car it) "I") (append (gip:take it 10) (list "\\U+042D\\U+041E\\U+041C.\\U+0421\\U+041E") (gip:drop it 11)) it)) its))))
(setq $Q236 (gip:deep-u '(lambda (its) (mapcar '(lambda (it / p rx ry)
                              (if (and (= (car it) "E") (= (gip:it-get it 0) "MTEXT"))
                                (progn (setq p (assoc 10 (cdr it)) rx (- (cadr p) fx) ry (- (caddr p) fy))
                                       (cond ((and (equal ry 1250.0 1.0) (equal rx -2750.0 1.0)) (gip:it-text it (gip:gn *gip:S* "stage" "\\U+0420")))
                                             ((and (equal ry 1250.0 1.0) (equal rx -2000.0 1.0)) (gip:it-text it no))
                                             ((and (equal ry 1250.0 1.0) (equal rx -1150.0 1.0)) (gip:it-text it tot))
                                             (T it)))
                                it)) its))))
(setq $S237 (gip:u "\\U+043E\\U+0431\\U+0449\\U+0438\\U+0435 \\U+0434\\U+0430\\U+043D\\U+043D\\U+044B\\U+0435"))
(setq $S238 (gip:u "\\U+043E\\U+0434\\U+043D\\U+043E\\U+043B\\U+0438\\U+043D\\U+0435\\U+0439\\U+043D"))
(setq $S239 (gip:u "\\U+0444\\U+0440\\U+0430\\U+0433\\U+043C\\U+0435\\U+043D\\U+0442"))
(setq $S240 (gip:u "\\U+043F\\U+043E\\U+0434\\U+0432\\U+043E\\U+0434\\U+0430"))
(setq $S241 (gip:u "\\U+0443\\U+0441\\U+043B\\U+043E\\U+0432\\U+043D\\U+044B\\U+0435"))
(setq $S242 (gip:u "\\U+0441\\U+0438\\U+043B\\U+043E\\U+0432\\U+044B\\U+043C\\U+0438"))
(setq $S243 (gip:u "\\U+043E\\U+0441\\U+0432\\U+0435\\U+0449\\U+0435\\U+043D\\U+0438\\U+044F"))
(setq $S244 (gip:u "\\U+0434\\U+0441\\U+0443\\U+043F"))
(setq $S245 (gip:u "\\U+043C\\U+043E\\U+043D\\U+0442\\U+0430\\U+0436\\U+043D"))
(setq $S246 (gip:u "\\U+0441\\U+043F\\U+0435\\U+0446\\U+0438\\U+0444\\U+0438\\U+043A\\U+0430\\U+0446"))
(setq $S247 (gip:u "\\U+042D\\U+041E\\U+041C_\\U+0421\\U+0445\\U+0435\\U+043C\\U+0430 \\U+043F\\U+043E\\U+0434\\U+0432\\U+043E\\U+0434\\U+0430 \\U+043A\\U+0430\\U+0431\\U+0435\\U+043B\\U+044F_GIP"))
(setq $S248 (gip:u "\\U+0430\\U+043F\\U+043F\\U+0430\\U+0440\\U+0430\\U+0442 \\U+0443\\U+043F\\U+0440\\U+0430\\U+0432\\U+043B\\U+0435\\U+043D\\U+0438\\U+044F \\U+0438 \\U+0437\\U+0430\\U+0449\\U+0438\\U+0442\\U+044B \\U+0432 \\U+0420\\U+0429"))
(setq $S249 (gip:u "GIP-\\U+0429\\U+0418\\U+0422: \\U+0432 \\U+044D\\U+0442\\U+043E\\U+043C \\U+0447\\U+0435\\U+0440\\U+0442\\U+0435\\U+0436\\U+0435 \\U+043D\\U+0435\\U+0442 \\U+0431\\U+043B\\U+043E\\U+043A\\U+043E\\U+0432 \\U+0448\\U+0430\\U+0431\\U+043B\\U+043E\\U+043D\\U+0430 \\U+0413\\U+0418\\U+041F.\n\\U+041E\\U+0442\\U+043A\\U+0440\\U+043E\\U+0439\\U+0442\\U+0435 \\U+0444\\U+0430\\U+0439\\U+043B GIP_EOM_Shablon (DXF/DWG \\U+0438\\U+0437 \\U+043A\\U+043E\\U+043C\\U+043F\\U+043B\\U+0435\\U+043A\\U+0442\\U+0430) \\U+0438 \\U+0437\\U+0430\\U+043F\\U+0443\\U+0441\\U+0442\\U+0438\\U+0442\\U+0435 \\U+043A\\U+043E\\U+043C\\U+0430\\U+043D\\U+0434\\U+0443 \\U+0432 \\U+043D\\U+0451\\U+043C."))
(setq $Q250 (gip:deep-u '(lambda (its) (mapcar '(lambda (it / t1 p rx ry)
                              (if (= (car it) "E")
                                (progn
                                  (setq t1 (gip:it-get it 1))
                                  (if (and (= (gip:it-get it 0) "MTEXT") (setq p (assoc 10 (cdr it))))
                                    (setq rx (- (cadr p) (car Fm)) ry (- (caddr p) (cadr Fm))))
                                  (cond ((and t1 (gip:has t1 "\\U+041A\\U+043E\\U+043C\\U+043F\\U+043E\\U+043D\\U+043E\\U+0432\\U+043A\\U+0430 \\U+0449\\U+0438\\U+0442\\U+0430")) (gip:it-text it (strcat "\\U+041C\\U+043E\\U+043D\\U+0442\\U+0430\\U+0436\\U+043D\\U+0430\\U+044F \\U+0441\\U+0445\\U+0435\\U+043C\\U+0430 \\U+0449\\U+0438\\U+0442\\U+0430 " (gip:gn S "board" "\\U+0429\\U+0420"))))
                                        ((and rx (equal ry 1250.0 1.0) (equal rx -2000.0 1.0)) (gip:it-text it (itoa (+ 8 nOL))))
                                        ((and rx (equal ry 1250.0 1.0) (equal rx -2750.0 1.0)) (gip:it-text it (gip:gn S "stage" "\\U+0420")))
                                        ((and rx (equal ry 1250.0 1.0) (equal rx -1150.0 1.0)) (gip:it-text it ""))
                                        ((and rx (equal ry 625.0 1.0) (equal rx -6250.0 1.0)) (gip:it-text it (strcat "\\U+041C\\U+043E\\U+043D\\U+0442\\U+0430\\U+0436\\U+043D\\U+0430\\U+044F \\U+0441\\U+0445\\U+0435\\U+043C\\U+0430 \\U+0449\\U+0438\\U+0442\\U+0430 " (gip:gn S "board" "\\U+0429\\U+0420"))))
                                        (T it)))
                                it)) its))))
(setq $S251 (gip:u "\\U+041E\\U+0431\\U+0449\\U+0438\\U+0435 \\U+0434\\U+0430\\U+043D\\U+043D\\U+044B\\U+0435"))
(setq $S252 (gip:u "\\U+041C\\U+043E\\U+043D\\U+0442\\U+0430\\U+0436\\U+043D\\U+0430\\U+044F \\U+0441\\U+0445\\U+0435\\U+043C\\U+0430 \\U+0449\\U+0438\\U+0442\\U+0430 "))
(setq $S253 (gip:u "\\U+041B\\U+0438\\U+0441\\U+0442"))
(setq $S254 (gip:u "\\U+041D\\U+041E\\U+041C\\U+0418\\U+041D\\U+0410\\U+041B"))
(setq $Q255 (gip:deep-u '("C" "\\U+0421")))
(setq $Q256 (gip:deep-u '("A" "\\U+0410")))
(setq $Q257 (gip:deep-u '(("R" "\\U+042D\\U+041E\\U+041C_\\U+0420\\U+043E\\U+0437\\U+0435\\U+0442\\U+043A\\U+0438_GIP" "\\U+0440\\U+043E\\U+0437\\U+0435\\U+0442\\U+043A\\U+0438 \\U+0441\\U+0438\\U+043B\\U+043E\\U+0432\\U+044B\\U+0435") ("V" "\\U+042D\\U+041E\\U+041C_\\U+0412\\U+044B\\U+043A\\U+043B\\U+044E\\U+0447\\U+0430\\U+0442\\U+0435\\U+043B\\U+0438_GIP" "\\U+0432\\U+044B\\U+043A\\U+043B\\U+044E\\U+0447\\U+0430\\U+0442\\U+0435\\U+043B\\U+0438") ("C" "\\U+042D\\U+041E\\U+041C_\\U+0421\\U+0432\\U+0435\\U+0442\\U+0438\\U+043B\\U+044C\\U+043D\\U+0438\\U+043A\\U+0438_GIP" "\\U+0441\\U+0432\\U+0435\\U+0442\\U+0438\\U+043B\\U+044C\\U+043D\\U+0438\\U+043A\\U+0438"))))
(setq $S258 (gip:u "\\U+0420\\U+043E\\U+0437\\U+0435\\U+0442\\U+043A\\U+0430 \\U+0448\\U+0442\\U+0435\\U+043F\\U+0441\\U+0435\\U+043B\\U+044C\\U+043D\\U+0430\\U+044F \\U+0441\\U+0438\\U+043B\\U+043E\\U+0432\\U+0430\\U+044F, 16A, L+N+PE (1\\U+0424)"))
(setq $S259 (gip:u "\\U+0420\\U+043E\\U+0437\\U+0435\\U+0442\\U+043A\\U+0430 \\U+0448\\U+0442\\U+0435\\U+043F\\U+0441\\U+0435\\U+043B\\U+044C\\U+043D\\U+0430\\U+044F \\U+0441\\U+0438\\U+043B\\U+043E\\U+0432\\U+0430\\U+044F, 16A, 3L+N+PE (3\\U+0424)"))
(setq $S260 (gip:u "\\U+0412\\U+044B\\U+0432\\U+043E\\U+0434 380/220\\U+0412"))
(setq $S261 (gip:u "\\U+0420\\U+043E\\U+0437\\U+0435\\U+0442\\U+043A\\U+0430 USB, IP20"))
(setq $S262 (gip:u "\\U+0422\\U+0435\\U+0440\\U+043C\\U+043E\\U+0440\\U+0435\\U+0433\\U+0443\\U+043B\\U+044F\\U+0442\\U+043E\\U+0440 \\U+0422\\U+041F"))
(setq $S263 (gip:u "\\U+041B\\U+044E\\U+0447\\U+043E\\U+043A \\U+0432\\U+043D\\U+0443\\U+0442\\U+0440\\U+0438\\U+043F\\U+043E\\U+043B\\U+044C\\U+043D\\U+044B\\U+0439 \\U+0440\\U+043E\\U+0437\\U+0435\\U+0442\\U+043E\\U+0447\\U+043D\\U+044B\\U+0439 1 \\U+0440\\U+043E\\U+0437., 16A, L+N+PE, IP44"))
(setq $S264 (gip:u "\\U+041B\\U+044E\\U+0447\\U+043E\\U+043A \\U+0432\\U+043D\\U+0443\\U+0442\\U+0440\\U+0438\\U+043F\\U+043E\\U+043B\\U+044C\\U+043D\\U+044B\\U+0439 \\U+0440\\U+043E\\U+0437\\U+0435\\U+0442\\U+043E\\U+0447\\U+043D\\U+044B\\U+0439 2 \\U+0440\\U+043E\\U+0437., 16A, L+N+PE, IP44"))
(setq $S265 (gip:u "\\U+0420\\U+043E\\U+0437\\U+0435\\U+0442\\U+043A\\U+0430 \\U+0448\\U+0442\\U+0435\\U+043F\\U+0441\\U+0435\\U+043B\\U+044C\\U+043D\\U+0430\\U+044F \\U+0441\\U+0438\\U+043B\\U+043E\\U+0432\\U+0430\\U+044F, 16A, L+N+PE (1\\U+0424) IP44"))
(setq $S266 (gip:u "\\U+0412\\U+044B\\U+043A\\U+043B\\U+044E\\U+0447\\U+0430\\U+0442\\U+0435\\U+043B\\U+044C 1 \\U+043A\\U+043B\\U+0430\\U+0432\\U+0438\\U+0448\\U+043D\\U+044B\\U+0439, 1\\U+043F, 16\\U+0410"))
(setq $S267 (gip:u "\\U+0412\\U+044B\\U+043A\\U+043B\\U+044E\\U+0447\\U+0430\\U+0442\\U+0435\\U+043B\\U+044C 2 \\U+043A\\U+043B\\U+0430\\U+0432\\U+0438\\U+0448\\U+043D\\U+044B\\U+0439, 1\\U+043F, 16A"))
(setq $S268 (gip:u "\\U+0412\\U+044B\\U+043A\\U+043B\\U+044E\\U+0447\\U+0430\\U+0442\\U+0435\\U+043B\\U+044C 3 \\U+043A\\U+043B\\U+0430\\U+0432\\U+0438\\U+0448\\U+043D\\U+044B\\U+0439, 1\\U+043F, 16A"))
(setq $S269 (gip:u "\\U+041F\\U+0435\\U+0440\\U+0435\\U+043A\\U+043B\\U+044E\\U+0447\\U+0430\\U+0442\\U+0435\\U+043B\\U+044C 1 \\U+043A\\U+043B\\U+0430\\U+0432\\U+0438\\U+0448\\U+043D\\U+044B\\U+0439, 1\\U+043F, 16A"))
(setq $S270 (gip:u "\\U+041F\\U+0435\\U+0440\\U+0435\\U+043A\\U+043B\\U+044E\\U+0447\\U+0430\\U+0442\\U+0435\\U+043B\\U+044C 2 \\U+043A\\U+043B\\U+0430\\U+0432\\U+0438\\U+0448\\U+043D\\U+044B\\U+0439, 1\\U+043F, 16A"))
(setq $S271 (gip:u "\\U+0414\\U+0438\\U+043C\\U+043C\\U+0435\\U+0440"))
(setq $S272 (gip:u "\\U+0414\\U+0430\\U+0442\\U+0447\\U+0438\\U+043A \\U+0434\\U+0432\\U+0438\\U+0436\\U+0435\\U+043D\\U+0438\\U+044F"))
(setq $S273 (gip:u "\\U+0421\\U+0432\\U+0435\\U+0442\\U+0438\\U+043B\\U+044C\\U+043D\\U+0438\\U+043A \\U+043F\\U+043E\\U+0442\\U+043E\\U+043B\\U+043E\\U+0447\\U+043D\\U+044B\\U+0439"))
(setq $S274 (gip:u "\\U+0421\\U+0432\\U+0435\\U+0442\\U+0438\\U+043B\\U+044C\\U+043D\\U+0438\\U+043A \\U+043F\\U+043E\\U+0434\\U+0432\\U+0435\\U+0441\\U+043D\\U+043E\\U+0439"))
(setq $S275 (gip:u "\\U+0421\\U+0432\\U+0435\\U+0442\\U+0438\\U+043B\\U+044C\\U+043D\\U+0438\\U+043A \\U+043D\\U+0430\\U+0441\\U+0442\\U+043E\\U+043B\\U+044C\\U+043D\\U+044B\\U+0439 / \\U+043D\\U+0430\\U+043F\\U+043E\\U+043B\\U+044C\\U+043D\\U+044B\\U+0439"))
(setq $S276 (gip:u "\\U+0421\\U+0432\\U+0435\\U+0442\\U+0438\\U+043B\\U+044C\\U+043D\\U+0438\\U+043A \\U+0432\\U+0441\\U+0442\\U+0440\\U+0430\\U+0438\\U+0432\\U+0430\\U+0435\\U+043C\\U+044B\\U+0439"))
(setq $S277 (gip:u "\\U+0421\\U+0432\\U+0435\\U+0442\\U+0438\\U+043B\\U+044C\\U+043D\\U+0438\\U+043A \\U+043D\\U+0430\\U+043A\\U+043B\\U+0430\\U+0434\\U+043D\\U+043E\\U+0439"))
(setq $S278 (gip:u "\\U+0421\\U+0432\\U+0435\\U+0442\\U+0438\\U+043B\\U+044C\\U+043D\\U+0438\\U+043A \\U+043D\\U+0430\\U+0441\\U+0442\\U+0435\\U+043D\\U+043D\\U+044B\\U+0439"))
(setq $S279 (gip:u "\\U+0421\\U+0432\\U+0435\\U+0442\\U+0438\\U+043B\\U+044C\\U+043D\\U+0438\\U+043A \\U+0442\\U+0440\\U+0435\\U+043A\\U+043E\\U+0432\\U+044B\\U+0439"))
(setq $S280 (gip:u "\\U+0421\\U+0432\\U+0435\\U+0442\\U+0438\\U+043B\\U+044C\\U+043D\\U+0438\\U+043A \\U+043F\\U+043E\\U+0442\\U+043E\\U+043B\\U+043E\\U+0447\\U+043D\\U+044B\\U+0439 IP44"))
(setq $S281 (gip:u "\\U+0421\\U+0432\\U+0435\\U+0442\\U+0438\\U+043B\\U+044C\\U+043D\\U+0438\\U+043A \\U+0432\\U+0441\\U+0442\\U+0440\\U+0430\\U+0438\\U+0432\\U+0430\\U+0435\\U+043C\\U+044B\\U+0439 IP44"))
(setq $S282 (gip:u "\\U+0421\\U+0432\\U+0435\\U+0442\\U+0438\\U+043B\\U+044C\\U+043D\\U+0438\\U+043A \\U+043D\\U+0430\\U+043A\\U+043B\\U+0430\\U+0434\\U+043D\\U+043E\\U+0439 IP44"))
(setq $S283 (gip:u "\\U+0421\\U+0432\\U+0435\\U+0442\\U+0438\\U+043B\\U+044C\\U+043D\\U+0438\\U+043A \\U+043D\\U+0430\\U+0441\\U+0442\\U+0435\\U+043D\\U+043D\\U+044B\\U+0439 IP44"))
(setq $S284 (gip:u "\\U+0421\\U+0432\\U+0435\\U+0442\\U+0438\\U+043B\\U+044C\\U+043D\\U+0438\\U+043A \\U+0442\\U+0440\\U+0435\\U+043A\\U+043E\\U+0432\\U+044B\\U+0439 IP44"))
(setq $S285 (gip:u "\nGIP: \\U+043D\\U+0435\\U+0442 \\U+0444\\U+0430\\U+0439\\U+043B\\U+0430 \\U+043F\\U+043B\\U+0430\\U+043D\\U+0430 \\U+0438\\U+0437 PDF"))
(setq $S286 (gip:u "\nGIP: \\U+0444\\U+0430\\U+0439\\U+043B \\U+043F\\U+043B\\U+0430\\U+043D\\U+0430 \\U+043D\\U+0435 \\U+0440\\U+0430\\U+0441\\U+043F\\U+043E\\U+0437\\U+043D\\U+0430\\U+043D"))
(setq $S287 (gip:u "\nGIP: \\U+043F\\U+043E\\U+0434\\U+043B\\U+043E\\U+0436\\U+043A\\U+0430 \\U+043F\\U+043B\\U+0430\\U+043D\\U+0430..."))
(setq $S288 (gip:u "\n\\U+0413\\U+0418\\U+041F: \\U+0442\\U+043E\\U+0447\\U+043A\\U+0430 \\U+043B\\U+0435\\U+0432\\U+043E\\U+0433\\U+043E \\U+043D\\U+0438\\U+0436\\U+043D\\U+0435\\U+0433\\U+043E \\U+0443\\U+0433\\U+043B\\U+0430 \\U+043F\\U+043B\\U+0430\\U+043D\\U+0430: "))
(setq $S289 (gip:u "GIP_\\U+041F\\U+043E\\U+0434\\U+043B\\U+043E\\U+0436\\U+043A\\U+0430"))
(setq $S290 (gip:u "\n\\U+0413\\U+0418\\U+041F: \\U+043F\\U+043B\\U+0430\\U+043D \\U+0438\\U+0437 PDF \\U+2014 \\U+043F\\U+043E\\U+0434\\U+043B\\U+043E\\U+0436\\U+043A\\U+0430 \\U+00AB"))
(setq $S291 (gip:u "\\U+00BB ("))
(setq $S292 (gip:u " \\U+043E\\U+0431\\U+044A\\U+0435\\U+043A\\U+0442\\U+043E\\U+0432) \\U+043D\\U+0430 "))
(setq $S293 (gip:u " \\U+043B\\U+0438\\U+0441\\U+0442(\\U+0430\\U+0445), \\U+0431\\U+043B\\U+043E\\U+043A\\U+043E\\U+0432 \\U+0413\\U+0418\\U+041F: "))
(setq $S294 (gip:u ", \\U+043F\\U+0440\\U+0435\\U+0436\\U+043D\\U+0438\\U+0439 \\U+0438\\U+043C\\U+043F\\U+043E\\U+0440\\U+0442 \\U+0437\\U+0430\\U+043C\\U+0435\\U+043D\\U+0451\\U+043D"))
(setq $S295 (gip:u "\\U+041F\\U+043B\\U+0430\\U+043D \\U+0438\\U+0437 PDF (\\U+0444\\U+0430\\U+0439\\U+043B \\U+0438\\U+0437 \\U+043F\\U+0430\\U+043D\\U+0435\\U+043B\\U+0438 \\U+00AB\\U+041F\\U+043B\\U+0430\\U+043D \\U+0438\\U+0437 PDF\\U+00BB)"))
(setq $S296 (gip:u "\nGIP: \\U+0441\\U+0441\\U+044B\\U+043B\\U+043A\\U+0430 \\U+043D\\U+0430 \\U+0449\\U+0438\\U+0442 \\U+0432\\U+0437\\U+044F\\U+0442\\U+0430 \\U+0438\\U+0437 \\U+0431\\U+0443\\U+0444\\U+0435\\U+0440\\U+0430 \\U+043E\\U+0431\\U+043C\\U+0435\\U+043D\\U+0430."))
(setq $S297 (gip:u "\n\\U+0412\\U+0441\\U+0442\\U+0430\\U+0432\\U+044C\\U+0442\\U+0435 \\U+0441\\U+0441\\U+044B\\U+043B\\U+043A\\U+0443 \\U+043D\\U+0430 \\U+0449\\U+0438\\U+0442 \\U+0438\\U+0437 \\U+043A\\U+043E\\U+043D\\U+0441\\U+0442\\U+0440\\U+0443\\U+043A\\U+0442\\U+043E\\U+0440\\U+0430 gipproekt.ru: "))
(setq $S298 (gip:u "\nGIP-\\U+0429\\U+0418\\U+0422: \\U+043E\\U+0448\\U+0438\\U+0431\\U+043A\\U+0430 \\U+2014 "))
(setq $S299 (gip:u "\nGIP-\\U+0429\\U+0418\\U+0422: \\U+0430\\U+043B\\U+044C\\U+0431\\U+043E\\U+043C \\U+043F\\U+043E\\U+0441\\U+0442\\U+0440\\U+043E\\U+0435\\U+043D. \\U+0413\\U+0440\\U+0443\\U+043F\\U+043F: "))
(setq $S300 (gip:u ", \\U+0430\\U+043F\\U+043F\\U+0430\\U+0440\\U+0430\\U+0442\\U+043E\\U+0432: "))
(setq $S301 (gip:u ", \\U+0440\\U+0435\\U+0435\\U+043A: "))
(setq $S302 (gip:u ", \\U+043A\\U+043E\\U+0440\\U+043F\\U+0443\\U+0441 "))
(setq $Q303 (gip:deep-u '("\\U+0414\\U+0430" "\\U+041D\\U+0435\\U+0442")))
(setq $Q304 (gip:deep-u '("l_tpl" . "\\U+041A\\U+0432\\U+0430\\U+0440\\U+0442\\U+0438\\U+0440\\U+0430")))
(setq $Q305 (gip:deep-u '("l_area" . "\\U+041F\\U+043B\\U+043E\\U+0449\\U+0430\\U+0434\\U+044C \\U+043A\\U+0432\\U+0430\\U+0440\\U+0442\\U+0438\\U+0440\\U+044B, \\U+043C\\U+00B2 (\\U+0434\\U+043B\\U+044F \\U+0434\\U+043B\\U+0438\\U+043D \\U+043A\\U+0430\\U+0431\\U+0435\\U+043B\\U+0435\\U+0439)")))
(setq $Q306 (gip:deep-u '("l_ph" . "\\U+0412\\U+0432\\U+043E\\U+0434")))
(setq $Q307 (gip:deep-u '("l_inA" . "\\U+0412\\U+0432\\U+043E\\U+0434\\U+043D\\U+043E\\U+0439 \\U+0430\\U+0432\\U+0442\\U+043E\\U+043C\\U+0430\\U+0442, \\U+0410")))
(setq $Q308 (gip:deep-u '("l_inP" . "\\U+041F\\U+043E\\U+043B\\U+044E\\U+0441\\U+043E\\U+0432 \\U+0432\\U+0432\\U+043E\\U+0434\\U+043D\\U+043E\\U+0433\\U+043E (3 \\U+0444\\U+0430\\U+0437\\U+044B)")))
(setq $Q309 (gip:deep-u '("l_brand" . "\\U+041F\\U+0440\\U+043E\\U+0438\\U+0437\\U+0432\\U+043E\\U+0434\\U+0438\\U+0442\\U+0435\\U+043B\\U+044C \\U+0430\\U+0432\\U+0442\\U+043E\\U+043C\\U+0430\\U+0442\\U+0438\\U+043A\\U+0438")))
(setq $Q310 (gip:deep-u '("l_prot" . "\\U+0417\\U+0430\\U+0449\\U+0438\\U+0442\\U+0430 \\U+0433\\U+0440\\U+0443\\U+043F\\U+043F 30 \\U+043C\\U+0410")))
(setq $Q311 (gip:deep-u '("l_rail" . "\\U+0428\\U+0438\\U+0440\\U+0438\\U+043D\\U+0430 \\U+0440\\U+0435\\U+0439\\U+043A\\U+0438, \\U+043C\\U+043E\\U+0434\\U+0443\\U+043B\\U+0435\\U+0439")))
(setq $Q312 (gip:deep-u '("l_kc" . "\\U+041A\\U+043E\\U+044D\\U+0444\\U+0444\\U+0438\\U+0446\\U+0438\\U+0435\\U+043D\\U+0442 \\U+0441\\U+043F\\U+0440\\U+043E\\U+0441\\U+0430")))
(setq $Q313 (gip:deep-u '("l_relay" . "\\U+0420\\U+0435\\U+043B\\U+0435 \\U+043D\\U+0430\\U+043F\\U+0440\\U+044F\\U+0436\\U+0435\\U+043D\\U+0438\\U+044F")))
(setq $Q314 (gip:deep-u '("l_km" . "\\U+041C\\U+0430\\U+0441\\U+0442\\U+0435\\U+0440-\\U+0432\\U+044B\\U+043A\\U+043B\\U+044E\\U+0447\\U+0430\\U+0442\\U+0435\\U+043B\\U+044C (\\U+043A\\U+043E\\U+043D\\U+0442\\U+0430\\U+043A\\U+0442\\U+043E\\U+0440)")))
(setq $Q315 (gip:deep-u '("l_fire" . "\\U+0423\\U+0417\\U+041E \\U+043F\\U+0440\\U+043E\\U+0442\\U+0438\\U+0432\\U+043E\\U+043F\\U+043E\\U+0436\\U+0430\\U+0440\\U+043D\\U+043E\\U+0435 100 \\U+043C\\U+0410")))
(setq $Q316 (gip:deep-u '("l_fl" . "\\U+042D\\U+0442\\U+0430\\U+0436\\U+043D\\U+044B\\U+0439 \\U+0449\\U+0438\\U+0442 \\U+043D\\U+0430 \\U+0441\\U+0445\\U+0435\\U+043C\\U+0435")))
(setq $Q317 (gip:deep-u '("l_kup" . "\\U+041B\\U+0438\\U+043D\\U+0438\\U+044F \\U+041A\\U+0423\\U+041F (\\U+0443\\U+0440\\U+0430\\U+0432\\U+043D\\U+0438\\U+0432\\U+0430\\U+043D\\U+0438\\U+0435 \\U+043F\\U+043E\\U+0442\\U+0435\\U+043D\\U+0446\\U+0438\\U+0430\\U+043B\\U+043E\\U+0432)")))
(setq $Q318 (gip:deep-u '("l_floor" . "\\U+0422\\U+0451\\U+043F\\U+043B\\U+044B\\U+0439 \\U+043F\\U+043E\\U+043B, \\U+043B\\U+0438\\U+043D\\U+0438\\U+0439")))
(setq $Q319 (gip:deep-u '("l_ac" . "\\U+041A\\U+043E\\U+043D\\U+0434\\U+0438\\U+0446\\U+0438\\U+043E\\U+043D\\U+0435\\U+0440\\U+044B, \\U+0448\\U+0442.")))
(setq $Q320 (gip:deep-u '("l_heater" . "\\U+0412\\U+043E\\U+0434\\U+043E\\U+043D\\U+0430\\U+0433\\U+0440\\U+0435\\U+0432\\U+0430\\U+0442\\U+0435\\U+043B\\U+044C")))
(setq $Q321 (gip:deep-u '("l_hob" . "\\U+0412\\U+0430\\U+0440\\U+043E\\U+0447\\U+043D\\U+0430\\U+044F \\U+043F\\U+0430\\U+043D\\U+0435\\U+043B\\U+044C")))
(setq $Q322 (gip:deep-u '("l_oven" . "\\U+0414\\U+0443\\U+0445\\U+043E\\U+0432\\U+043E\\U+0439 \\U+0448\\U+043A\\U+0430\\U+0444")))
(setq $Q323 (gip:deep-u '("l_fridge" . "\\U+0425\\U+043E\\U+043B\\U+043E\\U+0434\\U+0438\\U+043B\\U+044C\\U+043D\\U+0438\\U+043A")))
(setq $Q324 (gip:deep-u '("l_dw" . "\\U+041F\\U+041C\\U+041C \\U+0438 \\U+0438\\U+0437\\U+043C\\U+0435\\U+043B\\U+044C\\U+0447\\U+0438\\U+0442\\U+0435\\U+043B\\U+044C")))
(setq $Q325 (gip:deep-u '("l_wash" . "\\U+0421\\U+0442\\U+0438\\U+0440\\U+0430\\U+043B\\U+044C\\U+043D\\U+0430\\U+044F \\U+043C\\U+0430\\U+0448\\U+0438\\U+043D\\U+0430")))
(setq $Q326 (gip:deep-u '("l_dry" . "\\U+0421\\U+0443\\U+0448\\U+0438\\U+043B\\U+044C\\U+043D\\U+0430\\U+044F \\U+043C\\U+0430\\U+0448\\U+0438\\U+043D\\U+0430")))
(setq $Q327 (gip:deep-u '("l_leak" . "\\U+0417\\U+0430\\U+0449\\U+0438\\U+0442\\U+0430 \\U+043E\\U+0442 \\U+043F\\U+0440\\U+043E\\U+0442\\U+0435\\U+0447\\U+0435\\U+043A \\U+0438 \\U+0441\\U+043B\\U+0430\\U+0431\\U+043E\\U+0442\\U+043E\\U+0447\\U+043D\\U+044B\\U+0439 \\U+0449\\U+0438\\U+0442")))
(setq $Q328 (gip:deep-u '("l_light" . "\\U+041E\\U+0441\\U+0432\\U+0435\\U+0449\\U+0435\\U+043D\\U+0438\\U+0435 \\U+2014 \\U+043F\\U+043E\\U+043C\\U+0435\\U+0449\\U+0435\\U+043D\\U+0438\\U+044F \\U+0447\\U+0435\\U+0440\\U+0435\\U+0437 \\U+0437\\U+0430\\U+043F\\U+044F\\U+0442\\U+0443\\U+044E")))
(setq $Q329 (gip:deep-u '("l_sock" . "\\U+0420\\U+043E\\U+0437\\U+0435\\U+0442\\U+043A\\U+0438 \\U+2014 \\U+0433\\U+0440\\U+0443\\U+043F\\U+043F\\U+044B \\U+0447\\U+0435\\U+0440\\U+0435\\U+0437 \\U+0437\\U+0430\\U+043F\\U+044F\\U+0442\\U+0443\\U+044E")))
(setq $Q330 (gip:deep-u '("l_board" . "\\U+041E\\U+0431\\U+043E\\U+0437\\U+043D\\U+0430\\U+0447\\U+0435\\U+043D\\U+0438\\U+0435 \\U+0449\\U+0438\\U+0442\\U+0430")))
(setq $Q331 (gip:deep-u '("l_stage" . "\\U+0421\\U+0442\\U+0430\\U+0434\\U+0438\\U+044F")))
(setq $Q332 (gip:deep-u '("b_link" . "\\U+0421\\U+0441\\U+044B\\U+043B\\U+043A\\U+0430 \\U+0441 \\U+0441\\U+0430\\U+0439\\U+0442\\U+0430\\U+2026")))
(setq $Q333 (gip:deep-u '("b_groups" . "\\U+0413\\U+0440\\U+0443\\U+043F\\U+043F\\U+044B\\U+2026")))
(setq $Q334 (gip:deep-u '("1 \\U+0444\\U+0430\\U+0437\\U+0430, 230 \\U+0412" "3 \\U+0444\\U+0430\\U+0437\\U+044B, 400/230 \\U+0412")))
(setq $Q335 (gip:deep-u '("\\U+0414\\U+0438\\U+0444\\U+0430\\U+0432\\U+0442\\U+043E\\U+043C\\U+0430\\U+0442\\U+044B \\U+043D\\U+0430 \\U+043B\\U+0438\\U+043D\\U+0438\\U+044F\\U+0445" "\\U+0423\\U+0417\\U+041E \\U+043D\\U+0430 \\U+0433\\U+0440\\U+0443\\U+043F\\U+043F\\U+044B \\U+043B\\U+0438\\U+043D\\U+0438\\U+0439")))
(setq $Q336 (gip:deep-u '("\\U+041D\\U+0435\\U+0442" "\\U+041D\\U+0430\\U+043A\\U+043E\\U+043F\\U+0438\\U+0442\\U+0435\\U+043B\\U+044C\\U+043D\\U+044B\\U+0439" "\\U+041F\\U+0440\\U+043E\\U+0442\\U+043E\\U+0447\\U+043D\\U+044B\\U+0439")))
(setq $Q337 (gip:deep-u '("\\U+0420 \\U+2014 \\U+0440\\U+0430\\U+0431\\U+043E\\U+0447\\U+0430\\U+044F" "\\U+041F \\U+2014 \\U+043F\\U+0440\\U+043E\\U+0435\\U+043A\\U+0442")))
(setq $S338 (gip:u "\\U+041F"))
(setq $S339 (gip:u " \\U+043A\\U+0412\\U+0442\t"))
(setq $Q340 (gip:deep-u '("l_gname" . "\\U+041D\\U+0430\\U+0438\\U+043C\\U+0435\\U+043D\\U+043E\\U+0432\\U+0430\\U+043D\\U+0438\\U+0435")))
(setq $Q341 (gip:deep-u '("l_gin" . "\\U+041D\\U+043E\\U+043C\\U+0438\\U+043D\\U+0430\\U+043B, \\U+0410")))
(setq $Q342 (gip:deep-u '("l_gcab" . "\\U+041A\\U+0430\\U+0431\\U+0435\\U+043B\\U+044C, \\U+043C\\U+043C\\U+00B2")))
(setq $Q343 (gip:deep-u '("l_gp" . "\\U+041C\\U+043E\\U+0449\\U+043D\\U+043E\\U+0441\\U+0442\\U+044C, \\U+043A\\U+0412\\U+0442")))
(setq $Q344 (gip:deep-u '("l_gph" . "\\U+0424\\U+0430\\U+0437\\U+0430")))
(setq $Q345 (gip:deep-u '("b_apply" . "\\U+041F\\U+0440\\U+0438\\U+043C\\U+0435\\U+043D\\U+0438\\U+0442\\U+044C")))
(setq $Q346 (gip:deep-u '("b_del" . "\\U+0423\\U+0434\\U+0430\\U+043B\\U+0438\\U+0442\\U+044C \\U+0433\\U+0440\\U+0443\\U+043F\\U+043F\\U+0443")))
(setq $Q347 (gip:deep-u '("b_add" . "\\U+0414\\U+043E\\U+0431\\U+0430\\U+0432\\U+0438\\U+0442\\U+044C \\U+0433\\U+0440\\U+0443\\U+043F\\U+043F\\U+0443")))
(setq $Q348 (gip:deep-u '("b_restore" . "\\U+0412\\U+0435\\U+0440\\U+043D\\U+0443\\U+0442\\U+044C \\U+0443\\U+0434\\U+0430\\U+043B\\U+0451\\U+043D\\U+043D\\U+044B\\U+0435")))
(setq $Q349 (gip:deep-u '("\\U+0430\\U+0432\\U+0442\\U+043E" "L1" "L2" "L3")))
(setq $S350 (gip:u "\\U+041D\\U+043E\\U+0432\\U+0430\\U+044F \\U+0433\\U+0440\\U+0443\\U+043F\\U+043F\\U+0430"))
(setq $S351 (gip:u "\nGIP: \\U+043D\\U+0435 \\U+0443\\U+0434\\U+0430\\U+043B\\U+043E\\U+0441\\U+044C \\U+043E\\U+0442\\U+043A\\U+0440\\U+044B\\U+0442\\U+044C \\U+043E\\U+043A\\U+043D\\U+043E"))
(setq $S352 (gip:u "\nGIP: \\U+0432 \\U+0441\\U+0441\\U+044B\\U+043B\\U+043A\\U+0435 \\U+043D\\U+0435\\U+0442 \\U+0441\\U+043E\\U+0441\\U+0442\\U+0430\\U+0432\\U+0430 \\U+0449\\U+0438\\U+0442\\U+0430 (#shchit=...)"))
(setq $S353 (gip:u "\nGIP-\\U+0429\\U+0418\\U+0422: \\U+0449\\U+0438\\U+0442 \\U+044D\\U+0442\\U+043E\\U+0433\\U+043E \\U+0447\\U+0435\\U+0440\\U+0442\\U+0435\\U+0436\\U+0430 \\U+0441\\U+043E\\U+0431\\U+0440\\U+0430\\U+043D \\U+0432 \\U+043F\\U+0430\\U+043D\\U+0435\\U+043B\\U+0438 \\U+00AB\\U+0413\\U+0440\\U+0443\\U+043F\\U+043F\\U+044B \\U+0449\\U+0438\\U+0442\\U+0430\\U+00BB. \\U+041A\\U+043D\\U+043E\\U+043F\\U+043A\\U+0430 \\U+041E\\U+041A \\U+0441\\U+043E\\U+0431\\U+0435\\U+0440\\U+0451\\U+0442 \\U+0435\\U+0433\\U+043E \\U+0437\\U+0430\\U+043D\\U+043E\\U+0432\\U+043E \\U+043F\\U+043E \\U+0448\\U+0430\\U+0431\\U+043B\\U+043E\\U+043D\\U+0443."))
(setq $S354 (gip:u "\nGIP: \\U+0432 \\U+0447\\U+0435\\U+0440\\U+0442\\U+0435\\U+0436\\U+0435 \\U+0435\\U+0449\\U+0451 \\U+043D\\U+0435\\U+0442 \\U+0449\\U+0438\\U+0442\\U+0430 \\U+2014 \\U+0437\\U+0430\\U+043F\\U+0443\\U+0441\\U+0442\\U+0438\\U+0442\\U+0435 \\U+0413\\U+0418\\U+041F\\U+0429\\U+0418\\U+0422"))
(setq $S355 (gip:u "\nGIP-\\U+0429\\U+0418\\U+0422: \\U+043C\\U+043E\\U+043D\\U+0442\\U+0430\\U+0436\\U+043D\\U+0430\\U+044F \\U+0441\\U+0445\\U+0435\\U+043C\\U+0430 \\U+0438\\U+0437\\U+043C\\U+0435\\U+043D\\U+0435\\U+043D\\U+0430 \\U+2014 \\U+043F\\U+0435\\U+0440\\U+0435\\U+0441\\U+0447\\U+0438\\U+0442\\U+044B\\U+0432\\U+0430\\U+044E \\U+043E\\U+0434\\U+043D\\U+043E\\U+043B\\U+0438\\U+043D\\U+0435\\U+0439\\U+043A\\U+0443 \\U+0438 \\U+0441\\U+043F\\U+0435\\U+0446\\U+0438\\U+0444\\U+0438\\U+043A\\U+0430\\U+0446\\U+0438\\U+044E\\U+2026"))
(setq $S356 (gip:u "\nGIP-\\U+0429\\U+0418\\U+0422: \\U+0430\\U+0432\\U+0442\\U+043E\\U+043E\\U+0431\\U+043D\\U+043E\\U+0432\\U+043B\\U+0435\\U+043D\\U+0438\\U+0435 \\U+0432\\U+043A\\U+043B\\U+044E\\U+0447\\U+0435\\U+043D\\U+043E \\U+2014 \\U+0434\\U+0432\\U+0438\\U+0433\\U+0430\\U+0439\\U+0442\\U+0435 \\U+0430\\U+043F\\U+043F\\U+0430\\U+0440\\U+0430\\U+0442\\U+044B \\U+043F\\U+043E \\U+0440\\U+0435\\U+0439\\U+043A\\U+0430\\U+043C, \\U+0441\\U+0445\\U+0435\\U+043C\\U+0430 \\U+043F\\U+0435\\U+0440\\U+0435\\U+0441\\U+0447\\U+0438\\U+0442\\U+0430\\U+0435\\U+0442\\U+0441\\U+044F \\U+0441\\U+0430\\U+043C\\U+0430."))
(setq $S357 (gip:u "\nGIP-\\U+0429\\U+0418\\U+0422: \\U+0430\\U+0432\\U+0442\\U+043E\\U+043E\\U+0431\\U+043D\\U+043E\\U+0432\\U+043B\\U+0435\\U+043D\\U+0438\\U+0435 \\U+0432\\U+044B\\U+043A\\U+043B\\U+044E\\U+0447\\U+0435\\U+043D\\U+043E \\U+2014 \\U+043F\\U+043E\\U+0441\\U+043B\\U+0435 \\U+043F\\U+0440\\U+0430\\U+0432\\U+043E\\U+043A \\U+0437\\U+0430\\U+043F\\U+0443\\U+0441\\U+043A\\U+0430\\U+0439\\U+0442\\U+0435 \\U+0413\\U+0418\\U+041F\\U+041E\\U+0411\\U+041D."))
(setq $S358 (gip:u "\\U+0413\\U+0418\\U+041F\\U+0429\\U+0418\\U+0422"))
(setq $S359 (gip:u "\\U+0413\\U+0418\\U+041F\\U+041E\\U+0411\\U+041D"))
(setq $S360 (gip:u "\\U+0413\\U+0418\\U+041F\\U+0421\\U+0421\\U+042B\\U+041B\\U+041A\\U+0410"))
(setq $S361 (gip:u "\\U+0413\\U+0418\\U+041F\\U+0410\\U+0412\\U+0422\\U+041E"))
(setq $S362 (gip:u "\\U+0413\\U+0418\\U+041F\\U+041F\\U+0410\\U+041D\\U+0415\\U+041B\\U+042C"))
(setq $S363 (gip:u "\\U+0413\\U+0418\\U+041F\\U+041F\\U+041B\\U+0410\\U+041D"))
(setq $S364 (gip:u "\nGIP-\\U+0429\\U+0418\\U+0422 \\U+0437\\U+0430\\U+0433\\U+0440\\U+0443\\U+0436\\U+0435\\U+043D. \\U+041A\\U+043E\\U+043C\\U+0430\\U+043D\\U+0434\\U+044B: \\U+0413\\U+0418\\U+041F\\U+0429\\U+0418\\U+0422 (GIPSHCHIT) \\U+2014 \\U+043F\\U+0430\\U+0440\\U+0430\\U+043C\\U+0435\\U+0442\\U+0440\\U+044B \\U+0438 \\U+043F\\U+043E\\U+0441\\U+0442\\U+0440\\U+043E\\U+0435\\U+043D\\U+0438\\U+0435 \\U+0430\\U+043B\\U+044C\\U+0431\\U+043E\\U+043C\\U+0430; \\U+0413\\U+0418\\U+041F\\U+041E\\U+0411\\U+041D (GIPUPD) \\U+2014 \\U+043F\\U+0435\\U+0440\\U+0435\\U+0441\\U+0447\\U+0451\\U+0442 \\U+043F\\U+043E \\U+043C\\U+043E\\U+043D\\U+0442\\U+0430\\U+0436\\U+043D\\U+043E\\U+0439 \\U+0441\\U+0445\\U+0435\\U+043C\\U+0435;"))
(setq $S365 (gip:u "\n  \\U+0413\\U+0418\\U+041F\\U+0421\\U+0421\\U+042B\\U+041B\\U+041A\\U+0410 (GIPLINK) \\U+2014 \\U+0449\\U+0438\\U+0442 \\U+043F\\U+043E \\U+0441\\U+0441\\U+044B\\U+043B\\U+043A\\U+0435 \\U+0438\\U+0437 \\U+043A\\U+043E\\U+043D\\U+0441\\U+0442\\U+0440\\U+0443\\U+043A\\U+0442\\U+043E\\U+0440\\U+0430 \\U+043D\\U+0430 \\U+0441\\U+0430\\U+0439\\U+0442\\U+0435; \\U+0413\\U+0418\\U+041F\\U+0410\\U+0412\\U+0422\\U+041E (GIPAUTO) \\U+2014 \\U+0430\\U+0432\\U+0442\\U+043E\\U+043E\\U+0431\\U+043D\\U+043E\\U+0432\\U+043B\\U+0435\\U+043D\\U+0438\\U+0435 \\U+0432\\U+043A\\U+043B/\\U+0432\\U+044B\\U+043A\\U+043B (\\U+0441\\U+0435\\U+0439\\U+0447\\U+0430\\U+0441 \\U+0432\\U+043A\\U+043B)."))
(setq $S366 (gip:u "\n  \\U+0413\\U+0418\\U+041F\\U+041F\\U+0410\\U+041D\\U+0415\\U+041B\\U+042C (GIPPANEL) \\U+2014 \\U+043F\\U+0430\\U+043D\\U+0435\\U+043B\\U+044C \\U+00AB\\U+0413\\U+0440\\U+0443\\U+043F\\U+043F\\U+044B \\U+0449\\U+0438\\U+0442\\U+0430\\U+00BB \\U+0440\\U+044F\\U+0434\\U+043E\\U+043C \\U+0441 \\U+0447\\U+0435\\U+0440\\U+0442\\U+0435\\U+0436\\U+043E\\U+043C (\\U+043D\\U+0443\\U+0436\\U+0435\\U+043D \\U+043F\\U+043B\\U+0430\\U+0433\\U+0438\\U+043D GIP.bundle)."))
;;; ============================================================================
;;; Справочники: производители, шаблоны квартир, сечения
;;; ============================================================================
(setq *gip:brands*
  (list
    (list "abb" '("name" . "ABB") '("c" . 14295834)
      '("a1" . "S201 C{I}") '("a2" . "S202 C{I}") '("a3" . "S203 C{I}") '("a4" . "S204 C{I}")
      '("dif" . "DS201 C{I} A30") '("dif4" . "DS203NC C{I} A30")
      '("rcd2" . "F202 A-{I}/0,03") '("rcd4" . "F204 A-{I}/0,03")
      '("fire2" . "F202 AC-{I}/0,1") '("fire4" . "F204 AC-{I}/0,1")
      '("km2" . "ESB 25-20") '("km4" . "ESB 25-40"))
    (list "iek" '("name" . "IEK") '("c" . 15906304)
      $Q1 $Q2 $Q3 $Q4
      $Q5 $Q6
      $Q7 $Q8
      $Q9 $Q10
      $Q11 $Q12)
    (list "dekraft" '("name" . "Dekraft") '("c" . 3120727)
      $Q13 $Q14 $Q15 $Q16
      $Q17 $Q18
      $Q19 $Q20
      $Q21 $Q22
      $Q23 $Q24)
    (list "chint" '("name" . "CHINT") '("c" . 2060241)
      '("a1" . "NXB-63 1P C{I}") '("a2" . "NXB-63 2P C{I}") '("a3" . "NXB-63 3P C{I}") '("a4" . "NXB-63 4P C{I}")
      $Q25 $Q26
      $Q27 $Q28
      $Q29 $Q30
      '("km2" . "NCH8-25/20") '("km4" . "NCH8-25/40"))))

(setq *gip:templates*
  (list
    (list "studio" $Q31 '("area" . 30.0)
      (cons "light" (list $S32 $S33 $S34))
      (cons "sockets" (list $S35 $S36 $S37)) '("floor" . 1) '("ac" . 1))
    (list "k1" $Q38 '("area" . 40.0)
      (cons "light" (list $S32 $S39 $S40 $S34))
      (cons "sockets" (list $S35 $S41 $S42 $S37)) '("floor" . 1) '("ac" . 1))
    (list "k2" $Q43 '("area" . 60.0)
      (cons "light" (list $S32 $S39 $S44 $S45 $S34))
      (cons "sockets" (list $S35 $S46 $S47 $S42 $S37)) '("floor" . 1) '("ac" . 2))
    (list "k3" $Q48 '("area" . 80.0)
      (cons "light" (list $S32 $S39 $S44 $S45 $S49 $S50 $S51))
      (cons "sockets" (list $S35 $S46 $S47 $S52 $S42 $S53 $S54)) '("floor" . 2) '("ac" . 3))))

(setq *gip:std-in* '(2 6 10 16 20 25 32 40 50 63 80 100))
(setq *gip:cable1* $Q55)
(setq *gip:cable3* $Q56)

;; модульные контакторы: тип (ток-контакты), ток, число НО-контактов, ширина в модулях (ABB ESB)
(setq *gip:km-types* '(("20-20" 20 2 1) ("25-20" 25 2 1) ("25-40" 25 4 2) ("40-20" 40 2 3) ("40-40" 40 4 3) ("63-20" 63 2 3) ("63-40" 63 4 3)))
(setq *gip:km-model* $Q57)
;; прокладка кабелей — вид блока «ЭОМ_Схема подвода кабеля_GIP»
(setq *gip:routes* $Q58)
;; корпуса ABB: ряд 12 модулей — UK600 (IP30), ряд 18 — Mistral41F (IP41); (имя рядов артикул)
(setq *gip:boxes* '((12 ("UK610" 1 "") ("UK620" 2 "") ("UK630" 3 "") ("UK640" 4 "") ("UK650" 5 ""))
                    (18 ("Mistral41F 18M" 1 "1SLM004102A1104") ("Mistral41F 36M" 2 "1SLM004102A1106")
                        ("Mistral41F 54M" 3 "1SLM004102A1109") ("Mistral41F 72M" 4 "1SLM004102A1110"))))

;; контактор по площади квартиры и числу фаз (3 фазы — 4 контакта), если не выбран вручную
(defun gip:km-auto (s / a)
  (setq a (gip:gn s "area" 60.0))
  (if (= (gip:g s "phases") 3)
    (cond ((<= a 70) "25-40") ((<= a 100) "40-40") (T "63-40"))
    (cond ((<= a 40) "20-20") ((<= a 70) "25-20") (T "40-20"))))
(defun gip:km-of (s / k r)
  (setq k (gip:g s "kmType"))
  (if (not (and (= (type k) 'STR) (setq r (assoc k *gip:km-types*)))) (setq r (assoc (gip:km-auto s) *gip:km-types*)))
  r)
(defun gip:km-model (s r / tpl)
  (setq tpl (gip:gn *gip:km-model* (gip:gn s "brand" "abb") (cdr (car *gip:km-model*))))
  (gip:repl (gip:repl (gip:repl tpl "{K}" (car r)) "{I}" (itoa (cadr r))) "{C}" (itoa (caddr r))))

;; корпус: наименьший с запасом 20 %, иначе наименьший, куда всё помещается (рейки — не меньше, чем на схеме)
(defun gip:pick-box (W used nrows / lst ok fit)
  (setq lst (cdr (assoc W *gip:boxes*)) ok nil fit nil)
  (foreach b lst
    (if (and (null ok) (>= (cadr b) nrows) (>= (* (cadr b) W) (* used 1.2))) (setq ok b))
    (if (and (null fit) (>= (cadr b) nrows) (>= (* (cadr b) W) used)) (setq fit b)))
  (if ok ok fit))

(defun gip:brand (key) (cdr (assoc key *gip:brands*)))
(defun gip:tpl (key) (cdr (assoc key *gip:templates*)))

(defun gip:cable-for (In poles light / v)
  (if light
    (if (= poles 3) $S59 $S60)
    (if (setq v (cdr (assoc In (if (= poles 3) *gip:cable3* *gip:cable1*)))) v $S61)))

(defun gip:fmt-model (tpl In) (gip:repl tpl "{I}" (itoa In)))

;; Состояние по умолчанию (как в конструкторе на сайте, ABB по умолчанию)
(defun gip:default-state (tplkey / t1)
  (setq t1 (gip:tpl tplkey))
  (list (cons "v" 1) (cons "tpl" tplkey) (cons "phases" (if (= tplkey "k3") 3 1)) (cons "inA" (if (= tplkey "k3") 25 40))
        (cons "inPoles" 3) (cons "brand" "abb") (cons "prot" "dif") (cons "relay" T) (cons "km" T) (cons "fire" nil)
        (cons "railW" 18) (cons "railsMin" 0) (cons "kc" 0.4)
        (cons "light" (gip:g t1 "light")) (cons "sockets" (gip:g t1 "sockets"))
        (cons "floor" (gip:g t1 "floor")) (cons "ac" (gip:g t1 "ac")) (cons "heater" "boiler")
        (cons "app" (list '("hob" . T) '("oven" . T) '("fridge" . T) '("dw" . T) '("wash" . T) '("dry" . nil) '("leak" . T)))
        (cons "custom" nil) (cons "removed" nil) (cons "edit" nil) (cons "order" nil) (cons "breaks" nil)
        (cons "area" (gip:g t1 "area")) (cons "kup" T) (cons "board" $S62) (cons "stage" $S63) (cons "floorShield" T)
        (cons "xb" nil) (cons "olLen" nil) (cons "route" $S64) (cons "kmType" nil)))
;;; ============================================================================
;;; Модель щита: групповые линии, аппараты, раскладка по рейкам, обозначения
;;; (перенос логики конструктора gipproekt.ru один в один)
;;; ============================================================================

(defun gip:line (id name cat prot poles In p / l)
  (list (cons "id" id) (cons "name" name) (cons "cat" cat) (cons "prot" prot) (cons "poles" poles) (cons "In" In) (cons "p" p)))

(defun gip:build-lines (s / LNS is3 app i n f a lst edit o light1 split3 rest k)
  (setq LNS nil is3 (= (gip:g s "phases") 3) app (gip:g s "app") edit (gip:g s "edit"))
  (setq i 0)
  (foreach n (gip:g s "light")
    (setq LNS (cons (gip:s (gip:line (strcat "light" (itoa i) ":" n) (strcat $S65 n) "light" "a" 1 10 0.3) "km" T) LNS) i (1+ i)))
  (if (gip:g app "hob")
    (setq LNS (cons (if is3 (gip:line "hob" $S66 "hob" "a" 3 16 7.5) (gip:line "hob" $S66 "hob" "a" 1 32 7.0)) LNS)))
  (if (gip:g app "oven") (setq LNS (cons (gip:line "oven" $S67 "app" "d" 1 16 3.5) LNS)))
  (if (gip:g app "fridge") (setq LNS (cons (gip:line "fridge" $S68 "app" "d" 1 16 0.5) LNS)))
  (if (gip:g app "dw") (setq LNS (cons (gip:line "dw" $S69 "app" "d" 1 16 2.2) LNS)))
  (if (gip:g app "wash") (setq LNS (cons (gip:line "wash" $S70 "app" "d" 1 16 2.3) LNS)))
  (if (gip:g app "dry") (setq LNS (cons (gip:line "dry" $S71 "app" "d" 1 16 2.5) LNS)))
  (setq i 0)
  (foreach n (gip:g s "sockets")
    (setq LNS (cons (gip:line (strcat "sock" (itoa i) ":" n) n "sock" "d" 1 16 1.5) LNS) i (1+ i)))
  (setq f 1)
  (while (<= f (gip:gn s "floor" 0))
    (setq LNS (cons (gip:line (strcat "floor" (itoa f)) (strcat $S72 (if (> (gip:g s "floor") 1) (strcat " " (itoa f)) "")) "floor" "d" 1 16 1.2) LNS) f (1+ f)))
  (cond ((= (gip:g s "heater") "boiler") (setq LNS (cons (gip:line "heater" $S73 "heat" "d" 1 16 2.0) LNS)))
        ((= (gip:g s "heater") "flow")
         (setq LNS (cons (if is3 (gip:line "heater" $S74 "heat" "d3" 3 16 9.0) (gip:line "heater" $S74 "heat" "d" 1 32 6.0)) LNS))))
  (if (gip:g app "leak") (setq LNS (cons (gip:line "leak" $S75 "leak" "d" 1 16 0.2) LNS)))
  (setq a 1)
  (while (<= a (gip:gn s "ac" 0))
    (setq LNS (cons (gip:line (strcat "ac" (itoa a)) (strcat $S76 (if (> (gip:g s "ac") 1) (strcat " " (itoa a)) "")) "ac" "a" 1 16 1.2) LNS) a (1+ a)))
  (foreach c (gip:g s "custom")
    (setq LNS (cons (gip:s (gip:line (gip:g c "id") (gip:g c "name") "custom" (gip:g c "prot") (gip:g c "poles") (gip:g c "In") (gip:g c "p")) "custom" T) LNS)))
  (setq LNS (reverse LNS))
  ;; правки пользователя
  (setq LNS (vl-remove-if '(lambda (l) (member (gip:g l "id") (gip:g s "removed"))) LNS))
  (setq LNS (mapcar $Q77 LNS))
  ;; фазы
  (if is3
    (progn
      (setq LNS (mapcar '(lambda (l) (if (= (gip:g l "poles") 3) (gip:s l "phase" "L123") l)) LNS))
      ;; освещение: по трём фазам по порядку
      (setq light1 (vl-remove-if-not '(lambda (l) (and (= (gip:g l "cat") "light") (= (gip:g l "poles") 1))) LNS))
      (setq n (length light1) k 0)
      (setq LNS (mapcar '(lambda (l / idx)
                         (if (setq idx (gip:index l light1))
                           (gip:s l "phase" (nth (min 2 (fix (/ (* idx 3.0) (max n 1)))) '("L1" "L2" "L3")))
                           l)) LNS))
      ;; остальные однофазные — тремя сплошными участками с ровной мощностью
      (setq rest (vl-remove-if-not '(lambda (l) (and (= (gip:g l "poles") 1) (/= (gip:g l "cat") "light"))) LNS))
      (setq LNS (gip:split3 LNS rest))
      (setq LNS (mapcar '(lambda (l / o) (setq o (gip:g edit (gip:g l "id")))
                         (if (and (gip:g o "phase") (= (gip:g l "poles") 1)) (gip:s l "phase" (gip:g o "phase")) l)) LNS)))
    (setq LNS (mapcar '(lambda (l) (gip:s l "phase" (if (= (gip:g l "poles") 3) "L123" "L"))) LNS)))
  LNS)

;; деление последовательности на три участка L1/L2/L3 (как split3 в конструкторе)
(defun gip:split3 (LNS arr / n pre i j a1 a2 a3 m cnt best k ids res)
  (setq n (length arr))
  (if (= n 0)
    LNS
    (progn
      (setq pre (list 0.0))
      (foreach l arr (setq pre (append pre (list (+ (last pre) (gip:g l "p"))))))
      (setq best nil i 0)
      (while (<= i n)
        (setq j i)
        (while (<= j n)
          (setq a1 (nth i pre) a2 (- (nth j pre) (nth i pre)) a3 (- (nth n pre) (nth j pre)))
          (setq m (max a1 a2 a3))
          (setq cnt (- (max i (- j i) (- n j)) (min i (- j i) (- n j))))
          (if (or (null best) (< m (- (car best) 1e-9)) (and (< (abs (- m (car best))) 1e-9) (< cnt (cadr best))))
            (setq best (list m cnt i j)))
          (setq j (1+ j)))
        (setq i (1+ i)))
      (setq ids (mapcar '(lambda (l) (gip:g l "id")) arr))
      (mapcar '(lambda (l / k)
                 (if (setq k (gip:index (gip:g l "id") ids))
                   (gip:s l "phase" (cond ((< k (nth 2 best)) "L1") ((< k (nth 3 best)) "L2") (T "L3")))
                   l)) LNS))))

(defun gip:std-up (v lst / r)
  (setq r nil)
  (foreach x lst (if (and (null r) (>= x v)) (setq r x)))
  (if r r (last lst)))

(defun gip:dev (pairs) pairs)

;; общие аппараты щита: ввод, реле, УЗО 100 мА, кросс-модуль, КМ (используют переменные вызывающей функции: b is3 useKm)
(defun gip:fixed-devs (s lines / D inPoles inP fi hasLight bn kt)
  (setq D nil)
  (setq inPoles (if is3 (if (= (gip:g s "inPoles") 4) 4 3) 2))
  (setq inP (if is3 (if (= inPoles 4) '("L1" "L2" "L3" "N") '("L1" "L2" "L3")) '("L" "N")))
  (setq bn (gip:g b "name"))
  (setq D (cons (list '("id" . "in") '("kind" . "in") (cons "w" inPoles) (cons "poles" inP) (cons "bot" inP) (cons "In" (gip:g s "inA"))
                      (cons "model" (gip:fmt-model (if is3 (if (= inPoles 4) (gip:g b "a4") (gip:g b "a3")) (gip:g b "a2")) (gip:g s "inA")))
                      $Q78 (cons "brand" bn) '("feed" . "ext")) D))
  (if (gip:g s "relay")
    (if is3
      (foreach p '("L1" "L2" "L3")
        (setq D (cons (list (cons "id" (strcat "rn" (substr p 2 1))) '("kind" . "rn") '("w" . 2) '("poles") '("bot" "L" "N" "Lo") (cons "phase" p) '("In" . 63)
                            $Q79 (cons "name" (strcat $S80 p)) '("brand" . "Welrok") '("feed" . "in")) D)))
      (setq D (cons (list '("id" . "rn1") '("kind" . "rn") '("w" . 2) '("poles") '("bot" "L" "N" "Lo") '("phase" . "L") '("In" . 63)
                          $Q79 $Q81 '("brand" . "Welrok") '("feed" . "in")) D))))
  (if (gip:g s "fire")
    (progn
      (setq fi (gip:std-up (max (gip:g s "inA") 40) '(40 63 80 100)))
      (setq D (cons (list '("id" . "fire") '("kind" . "fire") (cons "w" (if is3 4 2))
                          (cons "poles" (if is3 '("L1" "L2" "L3" "N") '("L" "N"))) (cons "bot" (if is3 '("L1" "L2" "L3" "N") '("L" "N")))
                          (cons "In" fi) (cons "model" (gip:fmt-model (if is3 (gip:g b "fire4") (gip:g b "fire2")) fi))
                          $Q82 (cons "brand" bn) '("feed" . "up")) D))))
  (if (gip:g s "xb")
    (setq D (cons (list '("id" . "xb") '("kind" . "xb") (cons "w" (if is3 5 3))
                        (cons "poles" (if is3 '("L1" "L2" "L3" "N") '("L" "N"))) (cons "bot" (if is3 '("L1" "L2" "L3" "N") '("L" "N")))
                        (cons "model" (if is3 $S83 $S84)) $Q85 $Q86 '("feed" . "up")) D)))
  (if useKm
    (progn
      (setq D (cons (list '("id" . "c2") '("kind" . "a1") '("w" . 1) '("poles" "L") '("bot" "L") (cons "phase" (if is3 "L1" "L")) '("In" . 2)
                          (cons "model" (gip:fmt-model (gip:g b "a1") 2)) $Q87 (cons "brand" bn) '("feed" . "src")) D))
      (setq kt (gip:km-of s))
      (setq D (cons (list '("id" . "km") '("kind" . "km") (cons "w" (nth 3 kt)) (cons "kmType" (car kt)) (cons "kmI" (cadr kt)) (cons "kmC" (caddr kt))
                          (cons "poles" (if is3 '("A1" "L1" "L2" "L3") '("A1" "L"))) (cons "bot" (if is3 '("A2" "L1" "L2" "L3") '("A2" "L")))
                          (cons "model" (gip:km-model s kt)) $Q88 (cons "brand" bn) '("feed" . "src")) D))))
  (reverse D))

;; аппараты щита (режим шаблона)
(defun gip:build-devices (s lines / b is3 D hasLight useKm rcdN ri run)
  (setq b (gip:brand (gip:g s "brand")) is3 (= (gip:g s "phases") 3))
  (setq hasLight (vl-some '(lambda (l) (gip:g l "km")) lines))
  (setq useKm (and (gip:g s "km") hasLight))
  (setq D (reverse (gip:fixed-devs s lines)))
  (setq rcdN 0 ri (max 40 (gip:std-up (gip:g s "inA") '(25 40 63 80))) run nil)
  (foreach l lines
    (cond
      ((gip:g l "km")
       (gip:flush-run) (setq D (cons (gip:line-dev l (if useKm "km" "src")) D)))
      ((and (= (gip:g s "prot") "rcd") (= (gip:g l "prot") "d") (= (gip:g l "poles") 1))
       (if (and run (/= (gip:g (car run) "phase") (gip:g l "phase"))) (gip:flush-run))
       (setq run (append run (list l))))
      (T (gip:flush-run) (setq D (cons (gip:line-dev l "src") D)))))
  (gip:flush-run)
  (reverse D))

;; вспомогательные функции build-devices (используют переменные вызывающей функции: D run rcdN ri b s)
(defun gip:line-dev (l feed / d)
  (setq d (list (cons "id" (strcat "L:" (gip:g l "id"))) (cons "line" l) (cons "name" (gip:g l "name")) (cons "In" (gip:g l "In"))
                (cons "phase" (gip:g l "phase")) (cons "feed" feed) (cons "brand" (gip:g b "name"))))
  (cond
    ((= (gip:g l "poles") 3)
     (if (= (gip:g l "prot") "d3")
       (setq d (append d (list '("kind" . "dif4") '("w" . 4) '("poles" "L1" "L2" "L3" "N") '("bot" "L1" "L2" "L3" "N")
                               (cons "model" (gip:fmt-model (gip:g b "dif4") (gip:g l "In"))))))
       (setq d (append d (list '("kind" . "a3") '("w" . 3) '("poles" "L1" "L2" "L3") '("bot" "L1" "L2" "L3")
                               (cons "model" (gip:fmt-model (gip:g b "a3") (gip:g l "In"))))))))
    ((and (= (gip:g l "prot") "d") (= (gip:g s "prot") "dif"))
     (setq d (append d (list '("kind" . "dif") '("w" . 2) '("poles" "L" "N") '("bot" "L" "N") (cons "model" (gip:fmt-model (gip:g b "dif") (gip:g l "In")))))))
    (T (setq d (append d (list '("kind" . "a1") '("w" . 1) '("poles" "L") '("bot" "L") (cons "model" (gip:fmt-model (gip:g b "a1") (gip:g l "In"))))))))
  d)

(defun gip:rcd-group (ls / rid ph)
  (setq rcdN (1+ rcdN) rid (strcat "rcd" (itoa rcdN) ":" (gip:g (car ls) "id")) ph (gip:g (car ls) "phase"))
  (setq D (cons (list (cons "id" rid) '("kind" . "rcd") '("w" . 2) '("poles" "L" "N") '("bot" "L" "N") (cons "phase" ph) (cons "In" ri)
                      (cons "model" (gip:fmt-model (gip:g b "rcd2") ri)) (cons "name" (strcat $S89 (itoa rcdN)))
                      (cons "brand" (gip:g b "name")) '("feed" . "src") (cons "rcdNo" rcdN)) D))
  (foreach l ls (setq D (cons (gip:s (gip:line-dev l rid) "rcdNo" rcdN) D))))

(defun gip:flush-run (/ g sz k)
  (if run
    (progn
      (setq g (gip:ceil (/ (length run) 4.0)) sz (gip:ceil (/ (length run) (float g))) k 0)
      (while (< k (length run))
        (gip:rcd-group (gip:take (gip:drop run k) sz))
        (setq k (+ k sz)))
      (setq run nil))))

;; порядок с учётом перетаскиваний: order — id по порядку, новые — после ближайшего предшественника
(defun gip:apply-order (s DEVS / order out used pos k idx byid j)
  (setq order (gip:g s "order"))
  (if (null order)
    DEVS
    (progn
      (setq out nil used nil)
      (foreach id order
        (foreach d DEVS (if (and (= (gip:g d "id") id) (not (member id used))) (setq out (append out (list d)) used (cons id used)))))
      (setq k 0)
      (foreach d DEVS
        (if (not (member (gip:g d "id") used))
          (progn
            (setq pos 0 idx (1- k))
            (while (>= idx 0)
              (if (and (= pos 0) (setq j (gip:index (nth idx DEVS) out))) (setq pos (1+ j) idx -1))
              (setq idx (1- idx)))
            (setq out (append (gip:take out pos) (list d) (gip:drop out pos)) used (cons (gip:g d "id") used))))
        (setq k (1+ k)))
      out)))

;; раскладка по рейкам
(defun gip:flow-rails (s DEVS / W rails cur used total need i d brk gw j nxt bx)
  (setq W (gip:g s "railW") rails nil cur nil used 0 i 0)
  (foreach d DEVS
    (setq brk (and (or (member (gip:g d "id") (gip:g s "breaks")) (member i (gip:g s "breakAt"))) cur))
    (setq gw (gip:g d "w"))
    (if (and (null (gip:g s "order")) (or (= (gip:g d "kind") "rcd") (= (gip:g d "id") "c2")))
      (progn
        (setq j (1+ i))
        (while (and (< j (length DEVS))
                    (progn (setq nxt (nth j DEVS))
                           (or (= (gip:g nxt "feed") (gip:g d "id"))
                               (and (= (gip:g d "id") "c2") (or (= (gip:g nxt "id") "km") (= (gip:g nxt "feed") "km"))))))
          (setq gw (+ gw (gip:g nxt "w")) j (1+ j)))
        (if (> gw W) (setq gw (gip:g d "w")))))
    (if (or brk (> (+ used gw) W)) (setq rails (append rails (list cur)) cur nil used 0))
    (setq cur (append cur (list d)) used (+ used (gip:g d "w")) i (1+ i)))
  (if cur (setq rails (append rails (list cur))))
  (setq total (gip:sum (mapcar '(lambda (d) (gip:g d "w")) DEVS)))
  (setq need (max (length rails) (gip:ceil (/ (* total 1.2) W))))
  (if (> (gip:gn s "railsMin" 0) 0) (setq need (max need (gip:g s "railsMin"))))
  ;; настоящий корпус ABB: реек на схеме столько же, сколько рядов в корпусе
  (if (setq bx (gip:pick-box W total (max need (length rails)))) (setq need (max need (cadr bx))))
  (while (< (length rails) need) (setq rails (append rails (list nil))))
  (list (cons "rails" rails) (cons "used" total) (cons "cap" (* (length rails) W)) (cons "box" bx)))

;; обозначения QF, QFD, QD, KV, KM, XT по порядку на рейках
(defun gip:designate (rails / c p r)
  (setq c '(("QF" . 0) ("QFD" . 0) ("QD" . 0) ("KV" . 0) ("KM" . 0) ("XT" . 0)))
  (mapcar '(lambda (r)
             (mapcar '(lambda (d / k p n)
                        (setq k (gip:g d "kind"))
                        (setq p (cond ((member k '("dif" "dif4")) "QFD") ((member k '("rcd" "fire")) "QD") ((= k "rn") "KV")
                                      ((= k "km") "KM") ((= k "xb") "XT") (T "QF")))
                        (setq n (1+ (gip:g c p)) c (gip:s c p n))
                        (gip:s d "ref" (strcat p (itoa n)))) r)) rails))

(defun gip:cos (l) (if (or (member (gip:g l "cat") '("hob" "heat" "floor")) (= (gip:gn l "key" (gip:g l "id")) "oven")) 1.0 0.9))

;; ориентировочная длина кабеля линии по площади квартиры, м
(defun gip:cable-len (l area / s cat k c)
  (setq s (sqrt (max area 15.0)) cat (gip:g l "cat"))
  ;; калибровка по проекту «Сосновая»: свет ~50 м на линию (шлейф по светильникам), розетки ~16 м, техника ~11 м
  (cond ((= cat "light") (setq k 4.0 c 10.0))
        ((= cat "sock") (setq k 1.2 c 4.0))
        ((member cat '("hob" "app" "floor" "heat" "leak")) (setq k 0.9 c 2.0))
        ((= cat "ac") (setq k 1.2 c 4.0))
        (T (setq k 1.2 c 4.0)))
  (gip:ceil (* (+ c (* k s)) 1.1)))

;; полный расчёт щита
(defun gip:board (s / lines devs flow rails all area v2)
  (setq v2 (= (gip:g s "v") 2))
  (setq lines (if v2 (gip:rows-lines s) (gip:build-lines s)) area (gip:gn s "area" 50.0))
  (setq lines (mapcar '(lambda (l) (if (gip:g l "len") l (gip:s l "len" (gip:cable-len l area)))) lines))
  (setq devs (if v2 (gip:rows-order s (gip:rows-devices s lines)) (gip:apply-order s (gip:build-devices s lines))))
  (setq flow (gip:flow-rails s devs))
  (setq rails (gip:designate (gip:g flow "rails")))
  (setq all (apply 'append rails))
  (list (cons "lines" lines) (cons "devs" devs) (cons "rails" rails) (cons "all" all) (cons "cap" (gip:g flow "cap")) (cons "used" (gip:g flow "used")) (cons "box" (gip:g flow "box"))))
;;; ============================================================================
;;; Состав щита из таблицы групп (панель AutoCAD): строки групп ("t" "g") и УЗО ("t" "u") по порядку
;;; слева направо. Группы под УЗО (защита "rcd") идут сразу за своим УЗО.
;;; Хранение: словарь чертежа GIPPANEL — JSON таблицы (только ASCII, русский как \uXXXX).
;;; ============================================================================

(setq *gip:row-cat* '(("light" . "light") ("elight" . "light") ("sock" . "sock") ("hob" . "hob") ("oven" . "app") ("app" . "app")
                      ("floor" . "floor") ("heat" . "heat") ("ac" . "ac") ("leak" . "leak") ("other" . "custom") ("reserve" . "custom")))

(defun gip:row-ser (cat) (cond ((= cat "elight") $S90) ((member cat '("light")) $S91) (T $S92)))
(defun gip:sec-for (In) (cond ((<= In 10) "1,5") ((<= In 20) "2,5") ((<= In 25) "4") ((<= In 32) "6") ((<= In 50) "10") (T "16")))
(defun gip:row-cable (r light / p)
  (setq p (gip:nz (gip:g r "poles") 1))
  (cond ((gip:g r "cable"))
        ((and (= (gip:g r "cat") "hob") (= p 3)) $S93)
        (light (if (= p 3) $S59 $S60))
        (T (strcat (if (= p 3) "5" "3") $S94 (gip:sec-for (gip:nz (gip:g r "In") 16))))))
(defun gip:num-float (v d) (cond ((numberp v) (float v)) (T d)))

;; строки таблицы -> групповые линии (поля как у gip:build-lines)
(defun gip:rows-lines (s / is3 rows cur cnt res r rc cat ser n p light ph l lens)
  (setq is3 (= (gip:g s "phases") 3) rows (gip:g s "rows") cur nil res nil)
  (setq cnt (list (cons $S91 0) (cons $S90 0) (cons $S92 0)))
  (foreach r rows
    (if (= (gip:g r "t") "u")
      (setq cur r)
      (progn
        (if (/= (gip:g r "prot") "rcd") (setq cur nil))
        (setq rc (gip:g r "cat") cat (gip:gn *gip:row-cat* rc "custom") ser (gip:row-ser rc))
        (setq n (1+ (gip:g cnt ser)) cnt (gip:s cnt ser n))
        (setq p (gip:nz (gip:g r "poles") 1) light (= cat "light"))
        (if (and (not is3) (= p 3)) (setq p 1))
        (setq ph (cond ((not is3) (if (= p 3) "L123" "L"))
                       ((= p 3) "L123")
                       ((and cur (/= (gip:g cur "poles") 4) (member (gip:g cur "phase") '("L1" "L2" "L3"))) (gip:g cur "phase"))
                       ((member (gip:g r "phase") '("L1" "L2" "L3")) (gip:g r "phase"))
                       (T "L1")))
        (setq l (list (cons "id" (gip:g r "id")) (cons "name" (gip:gn r "name" $S95)) (cons "cat" cat) (cons "rcat" rc)
                      (cons "prot" (cond ((= (gip:g r "prot") "av") "a") ((and (= (gip:g r "prot") "dif") (= p 3)) "d3") (T "d")))
                      (cons "gprot" (gip:gn r "prot" "dif")) (cons "poles" p) (cons "In" (gip:nz (gip:g r "In") 16))
                      (cons "p" (if (= rc "reserve") 0.0 (gip:num-float (gip:g r "p") 0.0))) (cons "phase" ph)
                      (cons "cable" (if (= rc "reserve") "" (gip:row-cable r light)))
                      (cons "km" (and (gip:g s "km") (gip:g r "km") (/= (gip:g r "prot") "rcd")))
                      (cons "num" (strcat ser "-" (itoa n))) (cons "idn" (gip:nz (gip:g r "idn") 30))
                      (cons "rcd" (if (and cur (= (gip:g r "prot") "rcd")) (gip:g cur "id")))
                      (cons "key" (cond ((gip:g r "key")) ((= rc "oven") "oven") (T nil)))))
        (if (= rc "reserve") (setq l (append l (list (cons "reserve" T) (cons "len" 0)))))
        (if (and (/= rc "reserve") (numberp (gip:g r "len"))) (setq l (append l (list (cons "len" (gip:ceil (gip:g r "len")))))))
        (if (= rc "custom") (setq l (gip:s l "custom" T)))
        (setq res (cons l res)))))
  (reverse res))

;; модель аппарата с током утечки и типом УЗО
(defun gip:model-idn (m idn typ)
  (if (and idn (/= idn 30))
    (setq m (gip:repl (gip:repl (gip:repl m "/0,03" (strcat "/" (gip:repl (rtos (/ idn 1000.0) 2 (if (< idn 100) 2 1)) "." ","))) "A30" (strcat "A" (itoa idn))) $S96 (strcat (itoa idn) $S97))))
  (if (= typ "AC") (setq m (gip:repl m " A-" " AC-")))
  m)

;; строки таблицы -> аппараты щита в порядке строк
(defun gip:rows-devices (s lines / b is3 D useKm rcdN cur r l dv k w ps id rid lid)
  (setq b (gip:brand (gip:g s "brand")) is3 (= (gip:g s "phases") 3))
  (setq useKm (and (gip:g s "km") (vl-some '(lambda (l) (gip:g l "km")) lines)))
  (setq D (reverse (gip:fixed-devs s lines)) rcdN 0 cur nil)
  (foreach r (gip:g s "rows")
    (if (= (gip:g r "t") "u")
      (progn
        (setq rcdN (1+ rcdN) w (if (and is3 (= (gip:g r "poles") 4)) 4 2) rid (strcat "rcd:" (gip:g r "id")) cur rid)
        (setq ps (if (= w 4) '("L1" "L2" "L3" "N") '("L" "N")))
        (setq D (cons (list (cons "id" rid) '("kind" . "rcd") (cons "w" w) (cons "poles" ps) (cons "bot" ps)
                            (cons "phase" (cond ((= w 4) "L123") ((not is3) "L") ((member (gip:g r "phase") '("L1" "L2" "L3")) (gip:g r "phase")) (T "L1")))
                            (cons "In" (gip:nz (gip:g r "In") 40)) (cons "idn" (gip:nz (gip:g r "idn") 30)) (cons "type" (gip:gn r "type" "A"))
                            (cons "model" (gip:model-idn (gip:fmt-model (gip:g b (if (= w 4) "rcd4" "rcd2")) (gip:nz (gip:g r "In") 40)) (gip:nz (gip:g r "idn") 30) (gip:gn r "type" "A")))
                            (cons "name" (strcat $S89 (itoa rcdN))) (cons "brand" (gip:g b "name")) '("feed" . "src")
                            (cons "rcdNo" rcdN) (cons "row" (gip:g r "id"))) D)))
      (progn
        (setq lid (gip:g r "id") l (vl-some '(lambda (x) (if (= (gip:g x "id") lid) x)) lines))
        (if (/= (gip:g r "prot") "rcd") (setq cur nil))
        (setq dv (list (cons "id" (strcat "L:" lid)) (cons "line" l) (cons "name" (gip:g l "name")) (cons "In" (gip:g l "In"))
                      (cons "phase" (gip:g l "phase")) (cons "brand" (gip:g b "name")) (cons "row" lid) (cons "idn" (gip:g l "idn"))
                      (cons "feed" (cond ((and cur (= (gip:g r "prot") "rcd")) cur) ((and useKm (gip:g l "km")) "km") (T "src")))))
        (if (and cur (= (gip:g r "prot") "rcd")) (setq dv (append dv (list (cons "rcdNo" rcdN)))))
        (setq k (if (= (gip:g r "prot") "dif") (if (= (gip:g l "poles") 3) "dif4" "dif") (if (= (gip:g l "poles") 3) "a3" "a1")))
        (setq dv (append dv (cond ((= k "dif4") (list '("kind" . "dif4") '("w" . 4) '("poles" "L1" "L2" "L3" "N") '("bot" "L1" "L2" "L3" "N")))
                                ((= k "dif") (list '("kind" . "dif") '("w" . 2) '("poles" "L" "N") '("bot" "L" "N")))
                                ((= k "a3") (list '("kind" . "a3") '("w" . 3) '("poles" "L1" "L2" "L3") '("bot" "L1" "L2" "L3")))
                                (T (list '("kind" . "a1") '("w" . 1) '("poles" "L") '("bot" "L"))))))
        (setq dv (append dv (list (cons "model" (gip:model-idn (gip:fmt-model (gip:g b k) (gip:g l "In")) (if (member k '("dif" "dif4")) (gip:g l "idn")) nil)))))
        (setq D (cons dv D)))))
  (reverse D))

;; порядок: общие аппараты — на местах с монтажной схемы, групповые и УЗО — в порядке таблицы
(defun gip:rows-order (s lst / O seq)
  (if (null (gip:g s "order"))
    lst
    (progn
      (setq O (gip:apply-order s lst) seq (vl-remove-if-not '(lambda (x) (gip:g x "row")) lst))
      (mapcar '(lambda (x / y) (if (gip:g x "row") (progn (setq y (car seq) seq (cdr seq)) y) x)) O))))

;; ---------------------------------------------------------------- JSON (запись) — только ASCII
(defun gip:hex4 (n / h d r)
  (setq r "" h "0123456789ABCDEF")
  (repeat 4 (setq d (rem n 16) r (strcat (substr h (1+ d) 1) r) n (/ n 16)))
  r)
(defun gip:js-str (s / r)
  (if (null s) "null"
    (progn
      (setq r "")
      (foreach c (vl-string->list s)
        (setq r (strcat r (cond ((= c 34) "\\\"") ((= c 92) "\\\\") ((or (< c 32) (> c 126)) (strcat "\\u" (gip:hex4 c))) (T (chr c))))))
      (strcat "\"" r "\""))))
(defun gip:js-num (v / s)
  (cond ((null v) "null")
        ((= (type v) 'INT) (itoa v))
        ((not (numberp v)) "null")
        ((equal v (fix v) 1e-9) (itoa (fix v)))
        (T (setq s (rtos v 2 4))
           (while (and (vl-string-search "." s) (= (substr s (strlen s)) "0")) (setq s (substr s 1 (1- (strlen s)))))
           (if (= (substr s (strlen s)) ".") (setq s (substr s 1 (1- (strlen s)))))
           s)))
(defun gip:js-val (v typ)
  (cond ((= typ "s") (gip:js-str (if (= (type v) 'STR) v nil)))
        ((= typ "n") (gip:js-num v))
        ((= typ "i") (if (numberp v) (itoa (fix (+ v (if (minusp v) -0.5 0.5)))) "null"))
        ((= typ "b") (if v "true" "false"))
        (T "null")))
(defun gip:js-obj (al schema / parts)
  (setq parts nil)
  (foreach f schema
    (setq parts (cons (strcat (gip:js-str (car f)) ":" (gip:js-val (gip:g al (car f)) (cdr f))) parts)))
  (strcat "{" (gip:join (reverse parts) ",") "}"))
(setq *gip:js-board* '(("name" . "s") ("tpl" . "s") ("area" . "n") ("phases" . "i") ("inA" . "i") ("inPoles" . "i") ("brand" . "s")
                       ("relay" . "b") ("km" . "b") ("fire" . "b") ("kup" . "b") ("kc" . "n") ("kcMode" . "s") ("pAllowed" . "n")
                       ("mark" . "s") ("railW" . "i") ("mode" . "s") ("kmType" . "s") ("xb" . "b") ("olLen" . "b") ("route" . "s") ("phaseMode" . "s")
                       ("fsHide" . "b") ("fsPre" . "s") ("fsPreIn" . "i") ("fsMeter" . "s") ("fsMeterSpec" . "s") ("fsPost" . "s")
                       ("fsPostIn" . "i") ("fsRcdIn" . "i") ("fsIdn" . "i") ("fsMark" . "s") ("fsCable" . "n")))
(setq *gip:js-g* '(("t" . "s") ("id" . "s") ("cat" . "s") ("name" . "s") ("prot" . "s") ("poles" . "i") ("In" . "i") ("p" . "n") ("idn" . "i")
                   ("phase" . "s") ("lock" . "b") ("cable" . "s") ("len" . "n") ("km" . "b") ("key" . "s") ("pAuto" . "b")))
(setq *gip:js-u* '(("t" . "s") ("id" . "s") ("In" . "i") ("idn" . "i") ("type" . "s") ("poles" . "i") ("phase" . "s") ("lock" . "b")))

;; состояние таблицы (alist board + rows) -> JSON
(defun gip:panel-json (B rows seq)
  (strcat "{\"v\":2,\"seq\":" (itoa seq) ",\"board\":" (gip:js-obj B *gip:js-board*) ",\"rows\":["
          (gip:join (mapcar '(lambda (r) (gip:js-obj r (if (= (gip:g r "t") "u") *gip:js-u* *gip:js-g*))) rows) ",")
          "]}"))

;; щит параметров GIP-ЩИТ (S) -> поля board таблицы
(defun gip:panel-board (S / P)
  (setq P (gip:g S "panel"))
  (foreach kv (list (cons "name" (gip:gn S "board" $S62)) (cons "tpl" (gip:gn S "tpl" "k2")) (cons "area" (gip:gn S "area" 50.0))
                    (cons "phases" (gip:gn S "phases" 1)) (cons "inA" (gip:gn S "inA" 40)) (cons "inPoles" (gip:gn S "inPoles" 3))
                    (cons "brand" (gip:gn S "brand" "abb")) (cons "relay" (gip:g S "relay")) (cons "km" (gip:g S "km"))
                    (cons "fire" (gip:g S "fire")) (cons "kup" T) (cons "kc" (gip:gn S "kc" 0.4)) (cons "railW" (gip:gn S "railW" 18))
                    (cons "xb" (gip:g S "xb")) (cons "olLen" (gip:g S "olLen")) (cons "route" (gip:gn S "route" $S64)) (cons "kmType" (gip:g S "kmType"))
                    (cons "fsHide" (not (gip:g S "floorShield"))))
    (setq P (gip:s P (car kv) (cdr kv))))
  (if (null (gip:g P "kcMode")) (setq P (gip:s P "kcMode" "manual")))
  (if (null (gip:g P "mark")) (setq P (gip:s P "mark" $S98)))
  (if (null (gip:g P "mode")) (setq P (gip:s P "mode" (if (= (gip:g S "prot") "rcd") "rcd" "dif"))))
  (if (null (gip:g P "phaseMode")) (setq P (gip:s P "phaseMode" (gip:gn S "phaseMode" "manual"))))
  P)

;; щит, собранный окном ГИПЩИТ (по шаблону) -> строки таблицы
(defun gip:rows-from-board (S BRD / rows n un d l k rc prot ph rcds)
  (setq rows nil n 0 un 0 rcds nil)
  (foreach d (gip:g BRD "all")
    (setq k (gip:g d "kind"))
    (cond
      ((= k "rcd")
       (setq un (1+ un) rcds (cons (cons (gip:g d "id") (strcat "u" (itoa un))) rcds))
       (setq rows (cons (list '("t" . "u") (cons "id" (strcat "u" (itoa un))) (cons "In" (gip:g d "In")) '("idn" . 30) '("type" . "A") '("poles" . 2)
                              (cons "phase" (if (member (gip:g d "phase") '("L1" "L2" "L3")) (gip:g d "phase") "L1")) '("lock")) rows)))
      ((setq l (gip:g d "line"))
       (setq n (1+ n))
       (setq rc (cond ((= (gip:g l "cat") "light") "light") ((= (gip:g l "cat") "app") (if (= (gip:g l "id") "oven") "oven" "app"))
                      ((= (gip:g l "cat") "custom") "other") (T (gip:g l "cat"))))
       (setq prot (cond ((member k '("dif" "dif4")) "dif") ((and (gip:g d "feed") (gip:starts (gip:g d "feed") "rcd")) "rcd") (T "av")))
       (setq ph (gip:gn l "phase" "L"))
       (setq rows (cons (list '("t" . "g") (cons "id" (strcat "g" (itoa n))) (cons "cat" rc) (cons "name" (gip:g l "name")) (cons "prot" prot)
                              (cons "poles" (gip:g l "poles")) (cons "In" (gip:g l "In")) (cons "p" (gip:g l "p")) '("idn" . 30)
                              (cons "phase" (if (= ph "L123") "L123" ph)) '("lock") (cons "cable" (gip:g (gip:g (gip:g S "edit") (gip:g l "id")) "cable"))
                              '("len") (cons "km" (= (gip:g d "feed") "km"))
                              (cons "key" (if (member (gip:g l "id") '("hob" "oven" "fridge" "dw" "wash" "dry" "heater" "leak")) (gip:g l "id"))))
                        rows)))))
  (list (reverse rows) (+ n un)))

;; JSON таблицы для текущего щита
(defun gip:panel-text (S BRD / x)
  (if (= (gip:g S "v") 2)
    (gip:panel-json (gip:panel-board S) (gip:g S "rows") (max (gip:gn S "seq" 0) (length (gip:g S "rows"))))
    (progn (setq x (gip:rows-from-board S BRD))
           (gip:panel-json (gip:panel-board S) (car x) (cadr x)))))

;; JSON таблицы (разобранный) + прежнее состояние -> состояние GIP-ЩИТ
(defun gip:state-from-panel (j old / B S rows k)
  (setq B (gip:g j "board"))
  (setq S (if (and old (= (gip:g old "v") 2)) old
            (gip:s (gip:s (gip:s (if old old (gip:default-state (gip:gn B "tpl" "k2"))) "order" nil) "breaks" nil) "breakAt" nil)))
  (foreach k '("phases" "inA" "inPoles" "railW") (if (numberp (gip:g B k)) (setq S (gip:s S k (fix (gip:g B k))))))
  (if (= (type (gip:g B "brand")) 'STR) (setq S (gip:s S "brand" (gip:g B "brand"))))
  (foreach k '("relay" "km" "fire" "xb" "olLen") (setq S (gip:s S k (if (gip:g B k) T nil))))
  (setq S (gip:s S "kup" T))
  (setq S (gip:s S "kmType" (if (and (= (type (gip:g B "kmType")) 'STR) (assoc (gip:g B "kmType") *gip:km-types*)) (gip:g B "kmType"))))
  (setq S (gip:s S "route" (if (member (gip:g B "route") *gip:routes*) (gip:g B "route") (car *gip:routes*))))
  (setq S (gip:s S "phaseMode" (if (= (gip:g B "phaseMode") "abc") "abc" "manual")))
  (setq S (gip:s S "mark" (gip:gn B "mark" $S98)))
  ;; этажный щит: настройки из таблицы (пусто — авто)
  (setq S (gip:s S "floorShield" (not (gip:g B "fsHide"))))
  (foreach k '("fsPre" "fsPreIn" "fsMeter" "fsMeterSpec" "fsPost" "fsPostIn" "fsRcdIn" "fsIdn" "fsMark" "fsCable") (setq S (gip:s S k (gip:g B k))))
  (setq S (gip:s S "kc" (gip:num-float (gip:g B "kc") 0.4)))
  (setq S (gip:s S "area" (gip:num-float (gip:g B "area") 50.0)))
  (setq S (gip:s S "board" (gip:gn B "name" $S62)))
  (setq S (gip:s S "tpl" (gip:gn B "tpl" "k2")))
  (setq S (gip:s S "prot" (if (= (gip:g B "mode") "rcd") "rcd" "dif")))
  (setq rows (gip:g j "rows"))
  (setq S (gip:s S "rows" rows) S (gip:s S "v" 2) S (gip:s S "seq" (gip:nz (gip:g j "seq") 0)) S (gip:s S "panel" B))
  ;; для спецификации: помещения освещения (санузлы для КУП) и число линий тёплого пола
  (setq S (gip:s S "light" (mapcar $Q99
                                   (vl-remove-if-not '(lambda (r) (member (gip:g r "cat") '("light"))) rows))))
  (setq S (gip:s S "floor" (length (vl-remove-if-not '(lambda (r) (= (gip:g r "cat") "floor")) rows))))
  S)

;; ---------------------------------------------------------------- обмен с панелью
(setq *gip:panel-file* "gip_panel_in.json")
(defun gip:read-file (fn / f l s)
  (if (and fn (findfile fn) (setq f (open fn "r")))
    (progn (setq s "")
           (while (setq l (read-line f)) (setq s (strcat s l)))
           (close f) s)))
(defun gip:panel-save (S BRD)
  (gip:dict-put "GIPPANEL" (if *gip:panel-raw* *gip:panel-raw* (gip:panel-text S BRD)))
  (setq *gip:panel-raw* nil))

;; панель -> чертёж: таблица записана в TEMPPREFIX\gip_panel_in.json, строим альбом
(defun c:GIPPANELAPPLY (/ txt j S)
  (setq txt (gip:read-file (strcat (getvar "TEMPPREFIX") *gip:panel-file*)))
  (if (and txt (setq j (vl-catch-all-apply 'gip:json (list txt))) (not (vl-catch-all-error-p j)) (assoc "board" j))
    (progn
      (setq S (gip:state-from-panel j (gip:load-state)))
      (setq *gip:panel-raw* txt)
      (gip:run S)
      (setq *gip:panel-raw* nil))
    (princ $S100))
  (princ))

;; чертёж с щитом, собранным раньше окном ГИПЩИТ, -> таблица для панели (без перестроения)
(defun gip:panel-export (/ S)
  (if (and (null (gip:dict-get "GIPPANEL")) (setq S (gip:load-state)))
    (progn (setq *gip:b* (gip:brand (gip:g S "brand")))
           (gip:dict-put "GIPPANEL" (gip:panel-text S (gip:board S)))))
  (princ))

;; ---------------------------------------------------------------- монтажная схема -> строки таблицы
;; порядок УЗО-блоков и свободных групп — по месту их аппаратов на рейках; группы внутри блока — по своим местам.
;; items — аппараты монтажной схемы по порядку (id рейка x номинал)
(defun gip:rows-from-montage (S items / pos p rows units cur kill r id out cu)
  (setq pos nil p 0)
  (foreach it items (setq pos (cons (cons (car it) p) pos) p (1+ p)))
  (setq rows (gip:g S "rows") units nil cur nil kill nil)
  ;; удалённые с монтажной схемы аппараты
  (foreach r rows
    (setq id (gip:g r "id"))
    (if (null (assoc (if (= (gip:g r "t") "u") (strcat "rcd:" id) (strcat "L:" id)) pos)) (setq kill (cons id kill))))
  ;; единицы порядка: (место строка-УЗО-или-группа группы-блока)
  (foreach r rows
    (cond ((member (gip:g r "id") kill)
           (if (= (gip:g r "t") "u") (setq cur nil)))
          ((= (gip:g r "t") "u")
           (setq units (cons (list (cdr (assoc (strcat "rcd:" (gip:g r "id")) pos)) r nil) units) cur T))
          ((and cur (= (gip:g r "prot") "rcd"))
           (setq cu (car units) units (cons (list (car cu) (cadr cu) (append (caddr cu) (list r))) (cdr units))))
          (T
           (setq cur nil)
           (if (= (gip:g r "prot") "rcd") (setq r (gip:s r "prot" (if (member (gip:g r "cat") '("light" "elight" "hob" "ac" "reserve")) "av" "dif"))))
           (setq units (cons (list (cdr (assoc (strcat "L:" (gip:g r "id")) pos)) r nil) units)))))
  (setq units (gip:msort (reverse units) '(lambda (a b) (< (car a) (car b)))))
  (setq out nil)
  (foreach u units
    (setq out (append out (list (cadr u))))
    (if (caddr u)
      (setq out (append out (gip:msort (caddr u) '(lambda (a b) (< (cdr (assoc (strcat "L:" (gip:g a "id")) pos)) (cdr (assoc (strcat "L:" (gip:g b "id")) pos)))))))))
  ;; номиналы, исправленные на монтажной схеме
  (mapcar '(lambda (r / it In)
             (if (and (= (gip:g r "t") "g") (setq it (assoc (strcat "L:" (gip:g r "id")) items)) (setq In (gip:parse-in (nth 3 it))) (/= In (gip:g r "In")))
               (gip:s (gip:s r "In" In) "cable" nil)
               r)) out))
;;; ============================================================================
;;; Построение объектов: прототипы из рабочих файлов ГИП, сдвиг, правка текста,
;;; вставка динамических блоков по имени с видимостью и атрибутами
;;; ============================================================================
(setq *gip:app* "GIPGEN")          ; метка созданных объектов (xdata)
(setq *gip:dev-app* "GIPDEV")      ; метка аппаратов монтажной схемы (id аппарата)

;; углы TEXT/ATTDEF (поворот 50, наклон 51) и ARC (50, 51) в файлах ГИП записаны в градусах,
;; а entmake ждёт радианы (MTEXT 50 — уже радианы, вставки "I" пересчитывает gip:ins)
(defun gip:deg-fix (it / typ)
  (if (and (= (car it) "E") (member (setq typ (cdr (assoc 0 (cdr it)))) '("TEXT" "ATTDEF" "ARC")))
    (cons "E" (mapcar '(lambda (p) (if (and (member (car p) '(50 51)) (numberp (cdr p))) (cons (car p) (* (cdr p) (/ pi 180.0))) p)) (cdr it)))
    it))
(defun gip:protos ()
  (if (null *gip:protos*)
    (setq *gip:protos* (mapcar '(lambda (pr) (cons (car pr) (mapcar 'gip:deg-fix (cdr pr)))) (gip:deep-u *gip:protos-raw*))))
  *gip:protos*)
(defun gip:proto (name / p)
  (if (setq p (assoc name (gip:protos))) (cdr p) (progn (princ (strcat $S101 name)) nil)))

;; ---------------------------------------------------------------- сдвиг
(defun gip:shift-pt (p dx dy) (append (list (car p) (+ (cadr p) dx) (+ (caddr p) dy)) (cdddr p)))

(defun gip:shift-data (data dx dy / typ out firstH edge c)
  (setq typ (cdr (assoc 0 data)) out nil firstH T edge nil)
  (foreach p data
    (setq c (car p))
    (cond
      ((= typ "HATCH")
       (cond ((and (= c 10) (listp (cdr p)) firstH) (setq firstH nil out (cons p out)))
             ((and (= c 10) (listp (cdr p))) (setq out (cons (gip:shift-pt p dx dy) out)))
             ((= c 72) (setq edge (cdr p) out (cons p out)))
             ((and (= c 11) (listp (cdr p)) (= edge 1)) (setq out (cons (gip:shift-pt p dx dy) out)))
             (T (setq out (cons p out)))))
      ((and (= c 10) (listp (cdr p)) (member typ '("LINE" "LWPOLYLINE" "CIRCLE" "ARC" "ELLIPSE" "TEXT" "MTEXT" "SOLID" "POINT")))
       (setq out (cons (gip:shift-pt p dx dy) out)))
      ((and (= c 11) (listp (cdr p)) (member typ '("LINE" "TEXT" "SOLID")))
       (setq out (cons (gip:shift-pt p dx dy) out)))
      ((and (member c '(12 13)) (listp (cdr p)) (= typ "SOLID"))
       (setq out (cons (gip:shift-pt p dx dy) out)))
      (T (setq out (cons p out)))))
  (reverse out))

(defun gip:shift-item (it dx dy)
  (if (= (car it) "E")
    (cons "E" (gip:shift-data (cdr it) dx dy))
    (append (list (nth 0 it) (nth 1 it) (+ (nth 2 it) dx) (+ (nth 3 it) dy)) (gip:drop it 4))))

;; ---------------------------------------------------------------- правка данных
(defun gip:dset (data c v / p)
  (if (setq p (assoc c data)) (subst (cons c v) p data) (append data (list (cons c v)))))
(defun gip:dget (data c) (cdr (assoc c data)))
(defun gip:it-set (it c v) (cons "E" (gip:dset (cdr it) c v)))
(defun gip:it-get (it c) (gip:dget (cdr it) c))
(defun gip:it-type (it) (if (= (car it) "E") (gip:it-get it 0) "INSERT"))

;; экранирование текста MTEXT
(defun gip:mt-esc (s)
  (gip:repl (gip:repl (gip:repl (gip:repl s "\\" "\\\\") "{" "\\{") "}" "\\}") "\n" "\\P"))

;; содержимое MTEXT: префикс форматирования до последней ';' + текст + закрывающие скобки
(defun gip:mt-wrap (full text / i n pre post c)
  (setq n (strlen full) post "")
  (while (and (> n 0) (= (substr full n 1) "}")) (setq post (strcat post "}") n (1- n)))
  (setq pre "" i n)
  (while (> i 0)
    (if (and (= pre "") (= (substr full i 1) ";")) (setq pre (substr full 1 i)))
    (setq i (1- i)))
  (strcat pre (gip:mt-esc text) post))

(defun gip:it-text (it text / data typ full val chunks)
  (setq data (cdr it) typ (cdr (assoc 0 data)))
  (if (/= typ "MTEXT")
    (gip:it-set it 1 text)
    (progn
      (setq full "")
      (foreach p data (if (= (car p) 3) (setq full (strcat full (cdr p)))))
      (setq full (strcat full (gip:dget data 1)))
      (setq val (gip:mt-wrap full text))
      (gip:mt-set it val))))

;; записать готовое содержимое MTEXT (длинное — кусками по 250 в код 3)
(defun gip:mt-set (it val / data before after chunks seen)
  (setq data (vl-remove-if '(lambda (p) (= (car p) 3)) (cdr it)))
  (setq chunks nil)
  (while (> (strlen val) 250) (setq chunks (append chunks (list (cons 3 (substr val 1 250)))) val (substr val 251)))
  (setq before nil after nil seen nil)
  (foreach p data
    (cond ((= (car p) 1) (setq seen T))
          (seen (setq after (append after (list p))))
          (T (setq before (append before (list p))))))
  (cons "E" (append before chunks (list (cons 1 val)) after)))

(defun gip:it-line (it x1 y1 x2 y2 / d)
  (setq d (gip:dset (cdr it) 10 (list x1 y1 0.0)))
  (setq d (subst (list 10 x1 y1 0.0) (assoc 10 d) d))
  (setq d (subst (list 11 x2 y2 0.0) (assoc 11 d) d))
  (cons "E" d))

;; вершины полилинии: pts — плоский список x y x y ...
(defun gip:it-poly (it pts / data head tail mid n firstSeen k)
  (setq data (cdr it) head nil tail nil firstSeen nil)
  (foreach p data
    (cond ((member (car p) '(10 40 41 42 91))
           (setq firstSeen T))
          ((not firstSeen) (setq head (append head (list p))))
          (T (setq tail (append tail (list p))))))
  (setq mid nil k 0)
  (while (< k (length pts)) (setq mid (append mid (list (list 10 (nth k pts) (nth (1+ k) pts)))) k (+ k 2)))
  (setq head (subst (cons 90 (/ (length pts) 2)) (assoc 90 head) head))
  (cons "E" (append head mid tail)))

;; атрибуты вставки: в элементе "I" — список (тег . значение)
(defun gip:it-att (it tag val / atts)
  (if (= (car it) "I")
    (progn
      (setq atts (nth 12 it))
      (setq atts (if (assoc tag atts)
                   (mapcar '(lambda (a) (if (= (car a) tag) (cons tag val) a)) atts)
                   (append atts (list (cons tag val)))))
      (append (gip:take it 12) (list atts)))
    it))
(defun gip:it-atts (it pairs) (foreach p pairs (setq it (gip:it-att it (car p) (cdr p)))) it)

;; ---------------------------------------------------------------- создание
(defun gip:tag-list (tag) (list (list -3 (list *gip:app* (cons 1000 tag)))))

(defun gip:mk (data tag / e)
  (setq e (entmakex (append data (gip:tag-list tag))))
  (if (null e) (princ (strcat $S102 (vl-princ-to-string (cdr (assoc 0 data))))))
  e)

(defun gip:ms ()
  (if (null *gip:ms*) (setq *gip:ms* (vla-get-modelspace (vla-get-activedocument (vlax-get-acad-object)))))
  *gip:ms*)

(defun gip:layer (name)
  (if (not (tblsearch "LAYER" name))
    (entmakex (list '(0 . "LAYER") '(100 . "AcDbSymbolTableRecord") '(100 . "AcDbLayerTableRecord") (cons 2 name) '(70 . 0) '(62 . 7) '(6 . "Continuous"))))
  name)

(defun gip:set-dyn (obj name val / props r)
  (setq props (vl-catch-all-apply 'vlax-invoke (list obj 'GetDynamicBlockProperties)))
  (if (not (vl-catch-all-error-p props))
    (foreach p props
      (if (= (strcase (vlax-get p 'PropertyName)) (strcase name))
        (progn
          (setq r (vl-catch-all-apply 'vlax-put (list p 'Value val)))
          (if (vl-catch-all-error-p r) (princ (strcat $S103 name " = " (vl-princ-to-string val) ": " (vl-catch-all-error-message r)))))))))

(defun gip:set-atts (obj pairs / atts)
  (setq atts (vl-catch-all-apply 'vlax-invoke (list obj 'GetAttributes)))
  (if (not (vl-catch-all-error-p atts))
    (foreach a atts
      (foreach p pairs
        (if (= (strcase (vlax-get a 'TagString)) (strcase (car p)))
          (vlax-put a 'TextString (cdr p)))))))

(defun gip:visprop (name)
  (cond ((member name $Q104) $S105)
        ((= name $S106) $S107)
        ((= name "NUM-POM_GIP") "Visibility1")
        ((= name $S108) $S109)
        (T "Visibility")))

;; видимость: свойство, в списке значений которого есть нужное состояние (имя параметра не важно)
(defun gip:set-vis (obj name val / props done av r)
  (setq props (vl-catch-all-apply 'vlax-invoke (list obj 'GetDynamicBlockProperties)) done nil)
  (if (not (vl-catch-all-error-p props))
    (foreach p props
      (if (not done)
        (progn
          (setq av (vl-catch-all-apply 'vlax-get (list p 'AllowedValues)))
          (if (and (listp av) (member val av))
            (progn (setq r (vl-catch-all-apply 'vlax-put (list p 'Value val)) done T)
                   (if (vl-catch-all-error-p r) (princ (strcat "\nGIP: " name $S110 val $S111 (vl-catch-all-error-message r))))))))))
  (if (not done) (gip:set-dyn obj (gip:visprop name) val)))

;; вставка: ("I" имя x y sx sy rot° слой цвет масштаб_типа_линий видимость (свойства) (атрибуты))
(defun gip:ins (it tag / obj e ed name)
  (setq name (nth 1 it))
  (if (not (tblsearch "BLOCK" name))
    (progn (princ (strcat $S112 name $S113)) nil)
    (progn
      (setq obj (vla-insertblock (gip:ms) (vlax-3d-point (nth 2 it) (nth 3 it) 0.0) name (nth 4 it) (nth 5 it) (abs (nth 5 it)) (* (nth 6 it) (/ pi 180.0))))
      (gip:layer (nth 7 it))
      (foreach p (nth 11 it) (gip:set-dyn obj (car p) (cdr p)))
      (if (nth 10 it) (gip:set-vis obj name (nth 10 it)))
      (if (nth 12 it) (gip:set-atts obj (nth 12 it)))
      ;; слой, цвет, масштаб типа линий и метка — одной правкой
      (setq e (vlax-vla-object->ename obj) ed (entget e))
      (setq ed (gip:dset ed 8 (nth 7 it)))
      (if (nth 8 it) (setq ed (gip:dset ed 62 (nth 8 it))))
      (if (nth 9 it) (setq ed (gip:dset ed 48 (nth 9 it))))
      (entmod (append ed (gip:tag-list tag)))
      obj)))

(defun gip:emit (items tag / r)
  (setq r nil)
  (foreach it items
    (setq r (cons (if (= (car it) "E") (gip:mk (cdr it) tag) (gip:ins it tag)) r)))
  (reverse r))

;; place: прототип, сдвиг, правка (функция от списка элементов), создание
(defun gip:place (name dx dy fn / items)
  (setq items (mapcar '(lambda (it) (gip:shift-item it dx dy)) (gip:proto name)))
  (if fn (setq items (apply fn (list items))))
  (gip:emit items *gip:tag*))

;; MTEXT по прототипу с текстом и правками (o: ("w" . ширина) ("h" . высота) ("att" . привязка))
(defun gip:mt (proto x y text o / it)
  (gip:place proto x y
    (list 'lambda '(its / it)
      (list 'setq 'it '(car its))
      (if text (list 'setq 'it (list 'gip:it-text 'it text)))
      (if (assoc "w" o) (list 'setq 'it (list 'gip:it-set 'it 41 (float (cdr (assoc "w" o))))))
      (if (assoc "h" o) (list 'setq 'it (list 'gip:it-set 'it 40 (float (cdr (assoc "h" o))))))
      (if (assoc "att" o) (list 'setq 'it (list 'gip:it-set 'it 71 (cdr (assoc "att" o)))))
      '(cons it (cdr its)))))

(defun gip:W (x1 y1 x2 y2)
  (gip:place "wire" 0.0 0.0 (list 'lambda '(its) (list 'list (list 'gip:it-line '(car its) x1 y1 x2 y2)))))
(defun gip:PL (pts proto)
  (gip:place (if proto proto "wire0") 0.0 0.0 (list 'lambda '(its) (list 'list (list 'gip:it-poly '(car its) (list 'quote pts))))))
(defun gip:dot (x y big) (gip:place (if big "dot43" "dot41") x y nil))
;;; ============================================================================
;;; Принципиальная однолинейная схема (листы А3, как в рабочем файле ГИП)
;;; ============================================================================
(setq *gip:KU* 49.907)
(setq *gip:C0* 3631.0 *gip:PITCH* 785.4)
(setq *gip:YB_L* -1348.267 *gip:YB_N* -1437.39 *gip:YB_PE* -1527.18 *gip:YB_LB* -1619.82)
(setq *gip:YDEV* -1996.65 *gip:YDB* -2614.5 *gip:YKN* -2751.8 *gip:YMG* -2989.8)
(setq *gip:YT* '(-4547.0 -5144.0 -5442.0 -5740.0 -7075.0))

(defun gip:short-type (tpl / t1 p)
  ;; "S201 C{I}" -> "S201"; "ВА47-29 1Р C{I}" -> "ВА47-29"
  (setq t1 tpl)
  (if (setq p (vl-string-search " C{I}" t1)) (setq t1 (substr t1 1 p)))
  (if (setq p (vl-string-search "C{I}" t1)) (setq t1 (substr t1 1 p)))
  (if (setq p (vl-string-search " {I}" t1)) (setq t1 (substr t1 1 p)))
  (setq t1 (gip:trim t1))
  (foreach suf $Q114
    (if (gip:ends t1 suf) (setq t1 (substr t1 1 (- (strlen t1) (strlen suf))))))
  (gip:trim t1))

(defun gip:brand-ser (b kind In / tpl st)
  (setq tpl (gip:g b kind))
  (cond ((null tpl) "")
        ((= (substr kind 1 1) "a") (setq st (gip:short-type tpl)) (if (= (gip:g b "name") "ABB") (strcat st "C") st))
        ((member kind '("dif" "dif4")) (gip:short-type tpl))
        (T (gip:fmt-model tpl In))))
(defun gip:rcd-ser (tpl / p t1)
  (setq t1 tpl)
  (if (setq p (vl-string-search "{I}" t1)) (setq t1 (substr t1 1 p)))
  (setq t1 (vl-string-right-trim "- " t1))
  (gip:short-type t1))

;; марка кабеля в узкой колонке схемы: без «(А)» и дефиса — «ВВГнгLS», «ППГнгHF»
(defun gip:mark-short (m) (gip:repl (gip:repl (gip:repl m $S115 "") "(A)" "") "-" ""))
;; марка контактора -> две строки надписи: «ESB» + «25-40N», «КМ63-40М» + «25А», «NCH8» + «25/40»
(defun gip:km-split (m / p)
  (cond ((gip:starts m "ESB") (list "ESB" (substr m 4)))
        ((setq p (vl-string-search " " m)) (list (substr m 1 p) (gip:trim (substr m (+ p 2)))))
        ((setq p (vl-string-search "-" m)) (list (substr m 1 p) (substr m (+ p 2))))
        (T (list m ""))))
(defun gip:in-cable (In is3 / sq) (setq sq (cond ((<= In 25) 6) ((<= In 40) 10) (T 16))) (strcat $S116 (if is3 "5" "3") "x" (itoa sq)))
(defun gip:conduit (cab / sq p)
  (setq sq 2.5)
  (if (setq p (vl-string-search $S94 cab)) (setq sq (atof (gip:repl (substr cab (+ p 2)) "," "."))))
  (cond ((<= sq 1.5) $S117) ((<= sq 2.5) $S118) ((<= sq 6.0) $S119) (T $S120)))
(defun gip:next-in (v lst / r) (setq r nil) (foreach x lst (if (and (null r) (> x v)) (setq r x))) (if r r (last lst)))

(defun gip:consumer (l / nm wet)
  (setq nm (gip:lower (gip:gn l "name" "")))
  (cond ((= (gip:g l "cat") "light") '("c_svet" -4352.0 -4224.0))
        ((= (gip:g l "cat") "floor") '("c_tp" -4381.0 -4311.0))
        ((or (member (gip:g l "cat") '("sock" "app")) (and (= (gip:g l "cat") "custom") (/= (gip:g l "poles") 3)))
         (if (= (gip:gn l "key" (gip:g l "id")) "oven")
           '("c_kab" -4311.0 -4311.0)
           (progn
             (setq wet (or (gip:has nm $S121) (gip:has nm $S122) (gip:has nm $S123) (gip:has nm $S124) (gip:has nm $S125)
                           (member (gip:gn l "key" (gip:g l "id")) '("wash" "dw" "dry"))))
             (if wet '("c_roz44" -4311.0 -4311.0) '("c_roz" -4311.0 -4311.0)))))
        (T '("c_kab" -4311.0 -4311.0))))

(defun gip:inom (l / cc) (setq cc (gip:cos l))
  (if (= (gip:g l "poles") 3) (/ (gip:g l "p") (* (sqrt 3.0) 0.4 cc)) (/ (gip:g l "p") (* 0.23 cc))))

;; видимость вставки "I" (элемент 10)
(defun gip:it-vis (it v) (if (and v (= (car it) "I") (nth 10 it)) (append (gip:take it 10) (list v) (gip:drop it 11)) it))
;; видимость блока «аппарат управления и защиты в РЩ» по числу полюсов
(defun gip:av-vis (n) (strcat $S126 (nth (max 0 (min 3 (1- n))) $Q127)))
(defun gip:rcd-vis (four) (if four $S128 $S129))
;; атрибуты аппарата на схеме
(defun gip:dev-atts (its d o)
  (mapcar $Q130
          its))

;; колонки однолинейки и разбивка на листы по 19
(defun gip:ol-pages (B kup / cols nLO nLS pages cur i c need j CAP)
  (setq cols nil nLO 0 nLS 0 CAP 19)
  (foreach d (gip:g B "all")
    (cond ((= (gip:g d "kind") "rcd") (setq cols (cons (list '("t" . "rcd") (cons "d" d)) cols)))
          ((gip:g d "line")
           (cond ((gip:g (gip:g d "line") "num") (setq cols (cons (list '("t" . "line") (cons "d" d) (cons "no" (gip:g (gip:g d "line") "num"))) cols)))
                 ((= (gip:g (gip:g d "line") "cat") "light")
                  (setq nLO (1+ nLO) cols (cons (list '("t" . "line") (cons "d" d) (cons "no" (strcat $S131 (itoa nLO)))) cols)))
                 (T (setq nLS (1+ nLS) cols (cons (list '("t" . "line") (cons "d" d) (cons "no" (strcat $S132 (itoa nLS)))) cols)))))))
  (setq cols (reverse cols) pages nil cur nil i 0)
  (while (< i (length cols))
    (setq c (nth i cols) need 1)
    (if (= (gip:g c "t") "rcd")
      (progn (setq j (1+ i))
             (while (and (< j (length cols)) (= (gip:g (gip:g (nth j cols) "d") "feed") (gip:g (gip:g c "d") "id"))) (setq need (1+ need) j (1+ j)))))
    (if (and (> (+ (length cur) need) CAP) cur) (setq pages (append pages (list cur)) cur nil))
    (setq cur (append cur (list c)) i (1+ i)))
  (setq pages (append pages (list cur)))
  (if (and kup (>= (length (last pages)) CAP)) (setq pages (append pages (list nil))))
  pages)

;; ---------------------------------------------------------------- этажный щит
;; Настройки (поля fs* таблицы; пусто — авто). Селективность: автомат после счётчика — на ступень больше вводного
;; квартиры, УЗО — на ступень больше автомата, рубильник/автомат перед счётчиком — на ступень больше; при УЗО 100 мА
;; в квартире ток утечки в этажном щите — 300 мА.
(setq *gip:fs-brk* '(16 20 25 32 40 50 63 80 100 125) *gip:fs-qs* '(25 32 40 50 63 80 100 125) *gip:fs-rcd* '(25 40 63 80 100))
(defun gip:fs-int (S k) (if (numberp (gip:g S k)) (fix (gip:g S k))))
(defun gip:fs-str (S k) (if (and (= (type (gip:g S k)) 'STR) (/= (gip:trim (gip:g S k)) "")) (gip:trim (gip:g S k))))
(defun gip:sec-str (v) (if (equal v (fix v) 1e-9) (itoa (fix v)) (gip:repl (rtos v 2 1) "." ",")))
(defun gip:fs-cfg (S / is3 inA post postIn rcdIn idn pre preIn mark al sec)
  (setq is3 (= (gip:g S "phases") 3) inA (gip:gn S "inA" 40))
  (setq post (if (member (gip:g S "fsPost") '("av" "dif" "avrcd")) (gip:g S "fsPost") (if is3 "dif" "av")))
  (setq postIn (cond ((gip:fs-int S "fsPostIn")) (T (gip:next-in inA *gip:fs-brk*))))
  (setq rcdIn (if (= post "avrcd") (cond ((gip:fs-int S "fsRcdIn")) (T (gip:next-in postIn *gip:fs-rcd*)))))
  (setq idn (if (/= post "av") (cond ((gip:fs-int S "fsIdn")) ((gip:g S "fire") 300) (T 100))))
  (setq pre (if (= (gip:g S "fsPre") "qf") "qf" "qs"))
  (setq preIn (cond ((gip:fs-int S "fsPreIn")) (T (gip:next-in postIn (if (= pre "qs") *gip:fs-qs* *gip:fs-brk*)))))
  (setq mark (cond ((gip:fs-str S "fsMark")) ((gip:fs-str S "mark")) (T $S98)))
  (setq al (member (substr mark 1 1) $Q133))
  (setq sec (cond ((numberp (gip:g S "fsCable")) (gip:g S "fsCable"))
                  (al (cond ((<= inA 40) 16) ((<= inA 63) 25) (T 35)))
                  (T (cond ((<= inA 25) 6) ((<= inA 40) 10) (T 16)))))
  (list (cons "post" post) (cons "postIn" postIn) (cons "rcdIn" rcdIn) (cons "idn" idn) (cons "pre" pre) (cons "preIn" preIn)
        (cons "meter" (cond ((gip:fs-str S "fsMeter")) (is3 $S134) (T $S135)))
        (cons "meterSpec" (cond ((gip:fs-str S "fsMeterSpec")) (is3 $S136) (T $S137)))
        (cons "cable" (strcat mark " " (if is3 "5" "3") "x" (gip:sec-str sec)))))

;; оставляемые элементы прототипа (рамка, кабель с дугами, стояк, счётчик, PE) и детали аппаратов из floor3
(setq *gip:fs-keep* '(("floor3" 0 1 2 3 4 5 6 7 8 9 10 12 14 15 16 17 18 19 20 21 22 23 24 25 26 27 42 49 53)
                      ("floor1" 0 1 2 3 4 5 6 7 8 9 10 12 13 14 15 16 17 18 19 20 21 22 23 24 25 26 31 35 37)))
(setq *gip:fs-parts* '(("brk" "floor3" 5066.734974156 28 36 37 38 60 61 63 62)   ; автомат: нож L, контакт с крестом, расцепитель
                       ("brkN" "floor3" 5066.734974156 29 39 40 41 30 31)        ; второй полюс (N) автомата и связь ножей
                       ("rcdL" "floor3" 5066.734974156 28 36)                    ; полюс L УЗО
                       ("rcdN" "floor3" 5066.734974156 29 39 30 31)              ; полюс N УЗО и связь
                       ("diff" "floor3" 5066.734974156 32 33 34 35)              ; дифференциальный трансформатор
                       ("qs" "floor3" 6500.308914521 45 54 59)                   ; рубильник
                       ("sl3" "floor3" 5066.734974156 50 51 52) ("sl1" "floor3" 5066.734974156 51)
                       ("lbl1" "floor3" 6500.308914521 44)                       ; «QS 40А» над аппаратом перед счётчиком
                       ("lblQF" "floor1" 5066.734974156 49)                      ; «QF 50А» над автоматом после счётчика
                       ("lbl2a" "floor3" 5066.734974156 43) ("lbl2b" "floor3" 5066.734974156 13)))
(setq *gip:FS-LY* 1469.92215386 *gip:FS-NY* 1296.492577819 *gip:FS-BL* 216.787 *gip:FS-X* 4566.734974156)

(defun gip:fs-items (key x0 OX OY / p its)
  (setq p (assoc key *gip:fs-parts*) its (gip:proto (cadr p)))
  (mapcar '(lambda (i) (gip:shift-item (nth i its) (+ OX (- x0 (caddr p))) OY)) (cdddr p)))
(defun gip:fs-text (key x0 OX OY txt) (gip:emit (list (gip:it-text (car (gip:fs-items key x0 OX OY)) txt)) *gip:tag*))
;; аппарат: kind qs | qf | qfd | qd; x0 — начало ножа
(defun gip:fs-dev (kind x0 is3 OX OY / k)
  (foreach k (cond ((= kind "qs") '("qs")) ((= kind "qf") '("brk")) ((= kind "qfd") '("brk" "brkN" "diff")) (T '("rcdL" "rcdN" "diff")))
    (gip:emit (gip:fs-items k x0 OX OY) *gip:tag*))
  (gip:emit (gip:fs-items (if is3 "sl3" "sl1") x0 OX OY) *gip:tag*))
;; провод y от x1 до x2 с разрывами brk ((a b) ...)
(defun gip:fs-wire (y x1 x2 brk OX OY / tpl cur b)
  (setq tpl (nth 56 (gip:proto "floor3")) cur x1)
  (foreach b (gip:msort brk '(lambda (a c) (< (car a) (car c))))
    (if (> (car b) (+ cur 0.5)) (gip:emit (list (gip:it-poly tpl (list (+ OX cur) (+ OY y) (+ OX (car b)) (+ OY y)))) *gip:tag*))
    (setq cur (max cur (cadr b))))
  (if (> x2 (+ cur 0.5)) (gip:emit (list (gip:it-poly tpl (list (+ OX cur) (+ OY y) (+ OX x2) (+ OY y)))) *gip:tag*)))

(defun gip:floor-shield (S OX OY is3 / c name keep its it i p dm dq posts x0 kind brkL brkN pre lb)
  (setq c (gip:fs-cfg S) name (if is3 "floor3" "floor1") keep (cdr (assoc name *gip:fs-keep*)))
  ;; после счётчика: один аппарат на месте прототипа или автомат + УЗО (счётчик сдвигается вправо)
  ;; (счётчик и аппарат перед ним сдвигаются вправо, чтобы надписи не налезали)
  (if (= (gip:g c "post") "avrcd")
    (setq dm 300.0 dq 200.0 posts (list (list "qd" 4849.0) (list "qf" 5466.0)))
    (setq dm 0.0 dq 0.0 posts (list (list (if (= (gip:g c "post") "dif") "qfd" "qf") 5066.734974156))))
  (setq its (gip:proto name) lb nil)
  (foreach i keep
    (setq it (gip:shift-item (nth i its) OX OY))
    (cond ((= i 8) (setq it (gip:it-text it (gip:g c "cable"))))
          ((= i 12) (setq it (gip:it-att (gip:shift-item it dm 0.0) $S138 (gip:g c "meter"))))
          ((or (and is3 (= i 42)) (and (not is3) (= i 31))) (setq it (gip:it-text (gip:shift-item it dm 0.0) (gip:g c "meterSpec")))))
    (setq lb (cons it lb)))
  (gip:emit (reverse lb) *gip:tag*)
  ;; аппараты и надписи
  (setq brkL (list (list (+ 5783.521944339 dm) (+ 6000.308914521 dm))) brkN (list (list (+ 5783.521944339 dm) (+ 5997.145704499 dm))))
  (foreach p posts
    (setq kind (car p) x0 (cadr p))
    (gip:fs-dev kind x0 is3 OX OY)
    (setq brkL (cons (list x0 (+ x0 *gip:FS-BL*)) brkL))
    (if (member kind '("qfd" "qd")) (setq brkN (cons (list x0 (+ x0 *gip:FS-BL*)) brkN)))
    (cond ((= kind "qf") (gip:fs-text "lblQF" x0 OX OY (strcat "QF " (itoa (gip:g c "postIn")) $S139)))
          (T (gip:fs-text "lbl2a" x0 OX OY (if (= kind "qd") "QD" "QFD"))
             (gip:fs-text "lbl2b" x0 OX OY (strcat (itoa (if (= kind "qd") (gip:g c "rcdIn") (gip:g c "postIn"))) $S140 (itoa (gip:g c "idn")) $S97)))))
  (setq pre (gip:g c "pre") x0 (+ 6500.308914521 dq))
  (gip:fs-dev pre x0 is3 OX OY)
  (setq brkL (cons (list x0 (+ x0 *gip:FS-BL*)) brkL))
  (gip:fs-text "lbl1" x0 OX OY (strcat (if (= pre "qf") "QF " "QS ") (itoa (gip:g c "preIn")) $S139))
  ;; провода L и N (PE — из прототипа)
  (gip:fs-wire *gip:FS-LY* *gip:FS-X* 7728.927631497 brkL OX OY)
  (gip:fs-wire *gip:FS-NY* *gip:FS-X* 7593.090416282 brkN OX OY))

;; лист si однолинейной схемы с началом координат OX OY
(defun gip:ol-sheet (S BRD sc si npages OX OY / is3 b isfirst islast kup by km inD fire rns bname nC lastX XR XT XTr dxr nChain
                      sub chain y0 xi yb kk2 tx ty w1 hh px2 w2 HD hh2 phs Kc LNS spw sqv cosl ph PRAS Ip rows lb lxx rcdBus
                      ci x AX d l pl members xe yL yN srcY vr nY isD proto tk cs nmt AXk title titleF ks k1 k2 cn kk yy base px py rr q ii xx on)
  (setq is3 (= (gip:g S "phases") 3) b *gip:b* isfirst (= si 0) islast (= si (1- npages)) kup (gip:g S "kup"))
  (setq bname (gip:gn S "board" $S62))
  (setq km nil inD nil fire nil rns nil)
  (foreach d (gip:g BRD "all")
    (cond ((= (gip:g d "id") "km") (setq km d)) ((= (gip:g d "id") "in") (setq inD d)) ((= (gip:g d "id") "fire") (setq fire d))
          ((= (gip:g d "kind") "rn") (setq rns (append rns (list d))))))
  (gip:place "frame" OX OY nil)
  (gip:place "head" OX OY nil)
  (setq title (strcat $S141 bname (if (> npages 1) (strcat $S142 (itoa (1+ si))) "")))
  (gip:place (if is3 "shr3" "shr1") OX OY $Q143)
  (gip:place (if is3 "lbl3" "lbl1") OX OY nil)
  (setq nC (+ (length sc) (if (and islast kup) 1 0)))
  (setq lastX (+ *gip:C0* (* (max (1- nC) 0) *gip:PITCH*)))
  (setq XR (max (+ lastX 681.0) (+ *gip:C0* 681.0 *gip:PITCH*)))
  (setq XT (- (+ *gip:C0* (* (max nC 1) *gip:PITCH*)) 392.7))
  (setq dxr (- XR 18448.3))
  (gip:place "busL" OX OY '(lambda (its / it x1) (setq it (car its) x1 (cadr (assoc 10 (cdr it))))
                             (list (gip:it-poly it (list x1 (+ OY *gip:YB_L*) (+ OX XR) (+ OY *gip:YB_L*))))))
  (gip:place "busN" OX OY '(lambda (its / it p) (setq it (car its) p (assoc 11 (cdr it)))
                             (list (cons "E" (subst (list 11 (+ OX XR) (caddr p) (cadddr p)) p (cdr it))))))
  (gip:place "busPE" OX OY '(lambda (its / it p) (setq it (car its) p (assoc 11 (cdr it)))
                              (list (cons "E" (subst (list 11 (+ OX XR) (caddr p) (cadddr p)) p (cdr it))))))
  (gip:place "slashL" OX OY (if is3 nil '(lambda (its) (list (car its)))))
  (gip:place "slashR" (+ OX dxr) OY (if is3 nil '(lambda (its) (list (car its)))))
  (gip:place (if is3 "lblR3" "lblR1") (+ OX dxr) OY nil)
  (setq nChain (+ 1 (if rns 1 0) (if fire 1 0)))
  (setq yy (+ OY (if (and isfirst (> nChain 2)) 1010.0 449.9)))
  (gip:PL (list (+ OX 2385.5) yy (+ OX XR 323.0) yy (+ OX XR 323.0) (- OY 3176.0) (+ OX 2385.5) (- OY 3176.0) (+ OX 2385.5) yy) "rectDev")
  (gip:PL (list (+ OX 2385.5) (+ OY (nth 0 *gip:YT*)) (+ OX XT) (+ OY (nth 0 *gip:YT*)) (+ OX XT) (+ OY (nth 4 *gip:YT*)) (+ OX 2385.5) (+ OY (nth 4 *gip:YT*))) "rectTab")
  (setq XTr (if (and islast kup) (- (+ *gip:C0* (* (length sc) *gip:PITCH*)) 392.7) XT))
  (foreach r '(1 2 3) (gip:PL (list (+ OX 3238.3) (+ OY (nth r *gip:YT*)) (+ OX XTr) (+ OY (nth r *gip:YT*))) nil))
  ;; ---- ввод
  (if isfirst
    (progn
      (if (gip:g S "floorShield") (gip:floor-shield S OX OY is3))
      (setq chain (list (list (cons "p" (if is3 "in3" "dev_a1")) (cons "rel" is3) (cons "d" inD)
                              (cons "o" (list (cons "ser" (if is3 (gip:brand-ser b (if (= (gip:g S "inPoles") 4) "a4" "a3") nil) (gip:brand-ser b "a2" nil)))
                                              (cons "vis" (gip:av-vis (if is3 (if (= (gip:g S "inPoles") 4) 4 3) 2))))))))
      (if rns (setq chain (append chain (list (list (cons "p" (if is3 "rel3" "rel1")) (cons "rel" T) (cons "d" '(("In" . 63)))
                                                    (cons "o" (list (cons "ser" (if is3 "VIP-63 x3" "VIP-63")) '("maker" . "Welrok")
                                                                    (cons "ref" (gip:join (mapcar '(lambda (r) (gip:g r "ref")) rns) ", ")))))))))
      (if fire (setq chain (append chain (list (list (cons "p" (if is3 "dev_d3" "dev_d1")) (cons "rel" nil) (cons "d" fire)
                                                     (cons "o" (list '("ma" . "100") (cons "ser" (gip:rcd-ser (gip:g b (if is3 "fire4" "fire2")))) $Q144 (cons "vis" (gip:rcd-vis is3)))))))))
      (setq y0 (if (> (length chain) 2) 787.0 169.0) xi 3973.06 kk 0)
      (foreach cn chain
        (setq yy (- y0 (* kk 618.0)))
        (if (gip:g cn "rel")
          (setq px OX py (+ OY (if (= (gip:g cn "p") "in3") (- yy 168.7) (+ yy 449.4))))
          (setq px (+ OX xi) py (+ OY yy)))
        (setq rr cn)
        (gip:place (gip:g cn "p") px py '(lambda (its) (gip:dev-atts its (gip:g rr "d") (gip:g rr "o"))))
        (setq kk (1+ kk)))
      (setq yb (- y0 (* (length chain) 618.0)))
      (if (gip:g S "floorShield")
        (progn
          (gip:place "ln_Ltop" 0.0 0.0 '(lambda (its) (list (gip:it-line (car its) (+ OX xi) (+ OY y0) (+ OX xi) (+ OY 939.0)))))
          (gip:PL (list (+ OX 4137.8) (+ OY y0) (+ OX 4137.8) (+ OY 939.0)) "ln_Ntop")))
      (gip:PL (list (+ OX 4137.8) (+ OY *gip:YB_N*) (+ OX 4137.8) (+ OY yb)) "ln_Nbot")
      (gip:PL (list (+ OX xi) (+ OY yb) (+ OX xi) (+ OY *gip:YB_L*)) "ln_Lbot")
      (gip:PL (list (+ OX 4302.6) (+ OY *gip:YB_PE*) (+ OX 4302.6) (+ OY (if (gip:g S "floorShield") 939.0 yb))) "ln_PE")
      (gip:dot (+ OX xi) (+ OY *gip:YB_L*) T) (gip:dot (+ OX 4137.8) (+ OY *gip:YB_N*) T) (gip:dot (+ OX 4302.6) (+ OY *gip:YB_PE*) T)
      (if km
        (progn
          (setq ks (gip:km-split (gip:gn km "model" "")) k1 (car ks) k2 (cadr ks))
          (gip:place (if is3 "km3" "km1") OX OY '(lambda (its) (mapcar '(lambda (it / t1) (setq t1 (if (= (car it) "E") (gip:it-get it 1)))
                                                                               (cond ((= t1 "ESB") (gip:it-set it 1 k1)) ((= t1 "63-40N") (gip:it-set it 1 k2)) (T it))) its)))
          (gip:place "kmname" OX OY nil)))
      ;; ---- показатели
      (setq Kc (gip:gn S "kc" 0.4) LNS (gip:g BRD "lines"))
      (setq spw (gip:sum (mapcar '(lambda (l) (gip:g l "p")) LNS)))
      (setq sqv (gip:sum (mapcar '(lambda (l) (/ (gip:g l "p") (gip:cos l))) LNS)))
      (setq cosl (if (> sqv 0) (/ (gip:round (* (/ spw sqv) 100)) 100.0) 0.9))
      (setq ph (list (cons "A" 0.0) (cons "B" 0.0) (cons "C" 0.0)))
      (foreach l LNS
        (cond ((not is3) (setq ph (gip:s ph "A" (+ (gip:g ph "A") (gip:g l "p")))))
              ((= (gip:g l "phase") "L123") (foreach q '("A" "B" "C") (setq ph (gip:s ph q (+ (gip:g ph q) (/ (gip:g l "p") 3.0))))))
              (T (setq q (cdr (assoc (gip:g l "phase") '(("L1" . "A") ("L2" . "B") ("L3" . "C")))))
                 (setq ph (gip:s ph q (+ (gip:g ph q) (gip:g l "p")))))))
      (setq PRAS (* spw Kc) Ip (if is3 (/ PRAS (* (sqrt 3.0) 0.4 cosl)) (/ PRAS (* 0.23 cosl))))
      ;; таблица по фазам: при одной фазе — только столбец A без заголовка
      (setq phs (if is3 '("A" "B" "C") '("A")))
      (setq tx (+ OX 8400.0) ty (+ OY 3550.0) kk2 *gip:KU* w1 (* (if is3 85 41) kk2) hh (* 34 kk2) px2 (+ tx w1) w2 (* 118 kk2) HD 500.0 hh2 (+ HD (* 30 kk2)))
      (gip:PL (list tx ty (+ px2 w2) ty (+ px2 w2) (- ty hh2) tx (- ty hh2) tx ty) nil)
      (gip:PL (list tx (- ty HD) (+ tx w1) (- ty HD)) nil)
      (gip:PL (list px2 ty px2 (- ty hh2)) nil)
      (foreach mm (if is3 '(19 41 63) '(19)) (gip:PL (list (+ tx (* mm kk2)) ty (+ tx (* mm kk2)) (- ty hh2)) nil))
      (foreach mm '(10 20) (gip:PL (list tx (- ty HD (* mm kk2)) (+ tx w1) (- ty HD (* mm kk2))) nil))
      (setq ii 0)
      (if is3 (foreach t1 $Q145 (gip:ol-cell (+ tx (* (+ 30 (* ii 22)) kk2)) (- ty (/ HD 2)) t1 nil) (setq ii (1+ ii))))
      (foreach r (list $Q146 $Q147 $Q148) (gip:ol-cell (+ tx (* 9.5 kk2)) (- ty HD (* (cdr r) kk2)) (car r) nil))
      (setq ii 0)
      (foreach pp phs
        (setq xx (+ tx (* (+ 30 (* ii 22)) kk2)) on (member pp phs))
        (gip:ol-cell xx (- ty HD (* 5 kk2)) (if on (gip:f1 (gip:g ph pp)) $S149) nil)
        (gip:ol-cell xx (- ty HD (* 15 kk2)) (if on (gip:f1 (* (gip:g ph pp) Kc)) $S149) nil)
        (gip:ol-cell xx (- ty HD (* 25 kk2)) (if on (gip:f1 (/ (* (gip:g ph pp) Kc) (* 0.23 cosl))) $S149) nil)
        (setq ii (1+ ii)))
      (gip:mt "cell_qty" (+ px2 (/ w2 2)) (- ty (/ HD 2)) $S150 (list (cons "w" 5889.026) (cons "att" 5)))
      (setq rows (list (cons $S151 (if is3 "400/230" "230")) (cons $S152 (gip:f1 spw))
                       (cons $S153 (gip:f1 PRAS)) (cons $S154 (gip:f1 Ip))
                       (cons $S155 (gip:fmtz Kc 2)) (cons $S156 (gip:fmtz cosl 2))))
      (setq ii 0)
      (foreach rw rows
        (setq yy (- ty HD (* ii 5 kk2)))
        (gip:PL (list px2 yy (+ px2 w2) yy) nil)
        (gip:ol-cell (+ px2 (* 1.5 kk2)) (- yy (* 2.5 kk2)) (car rw) T)
        (gip:ol-cell (+ px2 (* 107.5 kk2)) (- yy (* 2.5 kk2)) (cdr rw) nil)
        (setq ii (1+ ii)))))
  ;; ---- шина освещения
  (setq lb (vl-remove-if-not '(lambda (c) (and (= (gip:g c "t") "line") (= (gip:g (gip:g c "d") "feed") "km"))) sc))
  (if (and isfirst km lb)
    (progn (setq lxx (+ *gip:C0* (* (gip:index (last lb) sc) *gip:PITCH*)))
           (gip:PL (list (+ OX 3053.5) (+ OY *gip:YB_LB*) (+ OX lxx) (+ OY *gip:YB_LB*)) "lightbus")))
  ;; ---- колонки
  (setq rcdBus nil ci 0)
  (foreach c sc
    (setq x (+ *gip:C0* (* ci *gip:PITCH*)) AX (+ OX x) d (gip:g c "d") l (gip:g d "line"))
    (gip:PL (list (- AX 392.7) (+ OY (nth 0 *gip:YT*)) (- AX 392.7) (+ OY (nth 4 *gip:YT*))) nil)
    (if is3
      (progn
        (setq pl (if (= (gip:g c "t") "rcd")
                   (if (= (gip:g d "w") 4) "ABC" (gip:gn (list '("L1" . "A") '("L2" . "B") '("L3" . "C")) (gip:g d "phase") ""))
                   (if (or (= (gip:g d "phase") "L123") (member (gip:g d "kind") '("a3" "dif4"))) "ABC"
                     (gip:gn (list '("L1" . "A") '("L2" . "B") '("L3" . "C")) (gip:g d "phase") ""))))
        (gip:mt "m_phase" (- AX (if (> (strlen pl) 1) 316.0 135.5)) (- OY 1868.0) pl nil)))
    (if (= (gip:g c "t") "rcd")
      (progn
        (setq members (vl-remove-if-not '(lambda (m) (= (gip:g (gip:g m "d") "feed") (gip:g d "id"))) sc))
        (setq xe (+ OX *gip:C0* (* (gip:index (last members) sc) *gip:PITCH*)) yL -1712.0 yN -1782.0)
        (gip:dot AX (+ OY *gip:YB_L*) nil) (gip:dot (+ AX 165) (+ OY *gip:YB_N*) nil)
        (gip:W AX (+ OY *gip:YB_L*) AX (+ OY *gip:YDEV*)) (gip:W (+ AX 165) (+ OY *gip:YB_N*) (+ AX 165) (+ OY *gip:YDEV*))
        (setq rr d)
        (gip:place "dev_d1" AX (+ OY *gip:YDEV*) $Q157)
        (gip:W AX (+ OY *gip:YDB*) AX (- OY 2700.0)) (gip:W AX (- OY 2700.0) (+ AX 250) (- OY 2700.0)) (gip:W (+ AX 250) (- OY 2700.0) (+ AX 250) (+ OY yL))
        (gip:W (+ AX 165) (+ OY *gip:YDB*) (+ AX 165) (- OY 2655.0)) (gip:W (+ AX 165) (- OY 2655.0) (+ AX 330) (- OY 2655.0)) (gip:W (+ AX 330) (- OY 2655.0) (+ AX 330) (+ OY yN))
        (gip:PL (list (+ AX 250) (+ OY yL) xe (+ OY yL)) "lightbus")
        (gip:W (+ AX 330) (+ OY yN) (+ xe 165) (+ OY yN))
        (setq rcdBus (cons (cons (gip:g d "id") (list yL yN)) rcdBus))
        (gip:mt "cell_qty" AX (- OY 4845.0) $S149 (list (cons "w" 700.0))))
      (progn
        (setq srcY *gip:YB_L* vr (cdr (assoc (gip:g d "feed") rcdBus)))
        (if (and (= (gip:g d "feed") "km") km) (setq srcY *gip:YB_LB*))
        (if vr (setq srcY (car vr)))
        (setq nY (if vr (cadr vr) *gip:YB_N*) isD (member (gip:g d "kind") '("dif" "dif4")))
        (setq proto (cond ((= (gip:g d "kind") "dif4") "dev_d3") ((= (gip:g d "kind") "dif") "dev_d1") ((= (gip:g d "kind") "a3") "dev_a3") (T "dev_a1")))
        (gip:dot AX (+ OY srcY) nil) (gip:dot (+ AX 165) (+ OY nY) nil) (gip:dot (+ AX 266) (+ OY *gip:YB_PE*) nil)
        (gip:W AX (+ OY srcY) AX (+ OY *gip:YDEV*)) (gip:W (+ AX 165) (+ OY nY) (+ AX 165) (+ OY *gip:YDEV*))
        (setq tk (gip:g d "kind") rr d)
        (gip:place proto AX (+ OY *gip:YDEV*)
          $Q158)
        (gip:W (+ AX 165) (+ OY *gip:YDB*) (+ AX 165) (+ OY *gip:YKN*)) (gip:W (+ AX 165) (+ OY *gip:YKN*) AX (+ OY *gip:YMG*))
        (gip:W (+ AX 266) (+ OY *gip:YB_PE*) (+ AX 266) (+ OY *gip:YKN*)) (gip:W (+ AX 266) (+ OY *gip:YKN*) AX (+ OY *gip:YMG*))
        (if (not (gip:g l "reserve"))
          (progn
            (setq cs (gip:consumer l))
            (gip:W AX (+ OY *gip:YDB*) AX (+ OY (caddr cs)))
            (setq rr (list c l))
            (gip:place (car cs) AX (+ OY (cadr cs))
              $Q159)
            (gip:mt "m_cable" (- AX 157.0) (- OY 4195.5) (strcat (gip:mark-short (gip:gn S "mark" $S98)) " " (gip:repl (gip:g l "cable") $S94 "x")) nil)
            ;; длина кабеля на схеме — по галочке «Длины кабелей на схеме»
            (gip:mt "m_cond" (+ AX 64.0) (- OY 4195.5) (strcat (gip:conduit (gip:g l "cable")) (if (gip:g S "olLen") (strcat " L=" (itoa (gip:g l "len")) $S160) "")) nil)))
        (gip:mt "cell_qty" AX (- OY 4845.0) (gip:g c "no") (list (cons "w" 700.0)))
        (gip:mt "cell_qty" AX (- OY 5293.0) (gip:f1 (gip:g l "p")) (list (cons "w" 700.0)))
        (gip:mt "cell_qty" AX (- OY 5591.0) (gip:f1 (gip:inom l)) (list (cons "w" 700.0)))
        (setq nmt (gip:take (gip:wrap (if (gip:starts (gip:g l "name") $S65) (strcat $S161 (substr (gip:g l "name") 12)) (gip:g l "name")) 16) 3))
        (gip:mt "m_name" (+ (- AX 300.0) (if (= (length nmt) 1) 120.0 0.0)) (- OY 7022.0) (gip:join nmt "\n") (list (cons "w" 1282.0)))))
    (setq ci (1+ ci)))
  ;; ---- КУП
  (if (and islast kup)
    (progn
      (setq AXk (+ OX *gip:C0* (* (length sc) *gip:PITCH*)))
      (gip:PL (list (- AXk 392.7) (+ OY (nth 0 *gip:YT*)) (- AXk 392.7) (+ OY (nth 4 *gip:YT*))) nil)
      (gip:dot AXk (+ OY *gip:YB_PE*) nil) (gip:W AXk (+ OY *gip:YB_PE*) AXk (- OY 4360.5))
      (gip:place "kup" AXk OY
        $Q162)))
  ;; ---- штамп
  (gip:stamp-st OX OY title (itoa (+ 2 si)) "")
  title)

(defun gip:ol-cell (x y txt left)
  (gip:mt (if left "cell_name" "cell_qty") x y txt (list (cons "w" (if left 0.0 1000.0)) (cons "att" (if left 4 5)))))

;; надписи основного штампа листа схемы: название, стадия, лист, листов
(defun gip:stamp-st (OX OY title no tot)
  (gip:mt "st_title" OX OY title nil)
  (gip:mt "st_stage" OX OY (gip:gn *gip:S* "stage" $S63) nil)
  (gip:mt "st_no" OX OY no nil)
  (if (and tot (/= tot "")) (gip:mt "st_no" (+ OX 850.0) OY tot (list (cons "w" 900.0)))))
;;; ============================================================================
;;; Монтажная схема: аппараты — блоки GIPM_* на DIN-рейках, провода, гребёнки,
;;; шины N и PE, бирки. Единицы расчёта — пункты трафаретов Visio (1 модуль = 50,2 pt),
;;; затем масштаб под лист А3.
;;; ============================================================================
(setq *gip:MW* 50.2 *gip:GH* 224.0 *gip:LANE* 9.0 *gip:RC* 9.0)
(setq *gip:netc* '(("L" . 15213083) ("L1" . 9128476) ("L2" . 1287480) ("L3" . 15213083) ("N" . 2060241) ("CTL" . 16088064)))

;; клеммы трафаретов (x уже в масштабе ширины блока, y от верха корпуса)
(setq *gip:st-term* '(
  ("dk_a1" 223.9 (("L" 25.1 20.0)) (("L" 25.1 204.0)))
  ("dk_a2" 223.9 (("L" 25.1 20.0) ("N" 75.3 20.0)) (("L" 25.1 204.0) ("N" 75.3 204.0)))
  ("dk_a3" 223.9 (("L1" 25.1 20.0) ("L2" 75.3 20.0) ("L3" 125.5 20.0)) (("L1" 25.1 204.0) ("L2" 75.3 204.0) ("L3" 125.5 204.0)))
  ("dk_a4" 223.9 (("L1" 25.1 20.0) ("L2" 75.3 20.0) ("L3" 125.5 20.0) ("N" 175.7 20.0)) (("L1" 25.1 204.0) ("L2" 75.3 204.0) ("L3" 125.5 204.0) ("N" 175.7 204.0)))
  ("dk_dif" 232.4 (("N" 25.1 20.0) ("L" 75.6 20.0)) (("N" 25.1 212.4) ("L" 75.6 212.4)))
  ("dk_dif4" 232.4 (("N" 25.1 20.0) ("L1" 76.0 20.0) ("L2" 127.0 20.0) ("L3" 177.5 20.0)) (("N" 25.1 212.5) ("L1" 76.0 212.5) ("L2" 127.0 212.5) ("L3" 177.5 212.5)))
  ("dk_rcd2" 223.9 (("L" 25.0 19.5) ("N" 76.0 19.5)) (("L" 25.0 204.4) ("N" 76.0 204.4)))
  ("dk_rcd4" 223.9 (("L1" 25.1 19.5) ("L2" 76.2 19.5) ("L3" 127.2 19.5) ("N" 178.6 19.5)) (("L1" 25.1 204.5) ("L2" 76.2 204.5) ("L3" 127.2 204.5) ("N" 178.6 204.5)))
  ("abb_km2" 249.4 (("L" 14.7 21.5) ("A1" 25.0 44.0)) (("L" 14.7 228.0) ("A2" 25.0 205.3)))
  ("abb_km4" 249.4 (("L1" 15.0 37.4) ("L2" 36.3 37.4) ("L3" 66.2 37.4) ("A1" 51.2 23.6)) (("L1" 15.0 212.0) ("L2" 36.3 212.0) ("L3" 66.2 212.0) ("A2" 51.2 225.9)))
  ("ab_a1" 249.4 (("L" 24.8 23.4)) (("L" 24.8 226.3)))
  ("ab_a2" 249.4 (("L" 24.8 23.4) ("N" 74.4 23.4)) (("L" 24.8 226.3) ("N" 74.4 226.3)))
  ("ab_a3" 249.4 (("L1" 24.8 23.4) ("L2" 74.4 23.4) ("L3" 124.0 23.4)) (("L1" 24.8 226.3) ("L2" 74.4 226.3) ("L3" 124.0 226.3)))
  ("ab_a4" 249.4 (("L1" 24.8 23.4) ("L2" 74.4 23.4) ("L3" 124.0 23.4) ("N" 173.6 23.4)) (("L1" 24.8 226.3) ("L2" 74.4 226.3) ("L3" 124.0 226.3) ("N" 173.6 226.3)))
  ("ab_dif" 249.4 (("L" 24.8 23.4) ("N" 74.4 23.4)) (("L" 24.8 226.3) ("N" 74.4 226.3)))
  ("ab_rcd2" 249.4 (("L" 24.8 23.4) ("N" 74.4 23.4)) (("L" 24.8 226.3) ("N" 74.4 226.3)))
  ("ab_fire2" 249.4 (("L" 24.8 23.4) ("N" 74.4 23.4)) (("L" 24.8 226.3) ("N" 74.4 226.3)))
  ("ab_rcd4" 249.4 (("L1" 24.8 23.4) ("L2" 74.4 23.4) ("L3" 124.0 23.4) ("N" 173.6 23.4)) (("L1" 24.8 226.3) ("L2" 74.4 226.3) ("L3" 124.0 226.3) ("N" 173.6 226.3)))
  ("ab_fire4" 249.4 (("L1" 24.8 23.4) ("L2" 74.4 23.4) ("L3" 124.0 23.4) ("N" 173.6 23.4)) (("L1" 24.8 226.3) ("L2" 74.4 226.3) ("L3" 124.0 226.3) ("N" 173.6 226.3)))
  ("ab_dif4" 249.4 (("L1" 24.9 23.4) ("L2" 74.8 23.4) ("L3" 124.8 23.4) ("N" 174.6 23.4)) (("L1" 24.9 226.3) ("L2" 74.8 226.3) ("L3" 124.8 226.3) ("N" 174.6 226.3)))
  ("ch_a1" 226.8 (("L" 25.5 17.0)) (("L" 25.5 209.6)))
  ("ch_a2" 226.8 (("L" 25.5 17.0) ("N" 76.5 17.0)) (("L" 25.5 209.6) ("N" 76.5 209.6)))
  ("ch_a3" 226.8 (("L1" 25.5 17.0) ("L2" 76.5 17.0) ("L3" 127.6 17.0)) (("L1" 25.5 209.6) ("L2" 76.5 209.6) ("L3" 127.6 209.6)))
  ("ch_a4" 226.8 (("L1" 25.5 17.0) ("L2" 76.5 17.0) ("L3" 127.6 17.0) ("N" 178.6 17.0)) (("L1" 25.5 209.6) ("L2" 76.5 209.6) ("L3" 127.6 209.6) ("N" 178.6 209.6)))
  ("ch_rcd2" 226.8 (("N" 25.5 17.0) ("L" 76.5 17.0)) (("N" 25.5 209.6) ("L" 76.5 209.6)))
  ("ch_rcd4" 226.8 (("N" 25.5 17.0) ("L1" 76.5 17.0) ("L2" 127.6 17.0) ("L3" 178.6 17.0)) (("N" 25.5 209.6) ("L1" 76.5 209.6) ("L2" 127.6 209.6) ("L3" 178.6 209.6)))
  ("rel_vip" 240.9 (("L" 25.5 21.6) ("N" 76.5 21.6)) (("Lo" 25.5 218.8)))))
;; ширина трафарета в пунктах (для пересчёта клемм на ширину аппарата)
(setq *gip:st-vbw* '(("dk_a1" . 50.2) ("dk_a2" . 100.3) ("dk_a3" . 150.5) ("dk_a4" . 200.7) ("dk_dif" . 101.5) ("dk_dif4" . 203.0)
  ("dk_rcd2" . 102.0) ("dk_rcd4" . 204.1) ("abb_km2" . 50.5) ("abb_km4" . 102.0) ("ab_a1" . 49.6) ("ab_a2" . 99.2) ("ab_a3" . 148.8)
  ("ab_a4" . 198.4) ("ab_dif" . 99.2) ("ab_dif4" . 199.6) ("ab_rcd2" . 99.2) ("ab_rcd4" . 198.4) ("ab_fire2" . 99.2) ("ab_fire4" . 198.4)
  ("ch_a1" . 51.0) ("ch_a2" . 102.0) ("ch_a3" . 153.1) ("ch_a4" . 204.1) ("ch_rcd2" . 102.0) ("ch_rcd4" . 204.1) ("rel_vip" . 102.0)))

(defun gip:stencil (d s is3 / k P n)
  (setq k (gip:g d "kind"))
  (cond
    ((= k "km") (if (> (gip:g d "w") 1) "abb_km4" "abb_km2"))
    ((= k "rn") "rel_vip")
    ((member (gip:g s "brand") '("abb" "chint"))
     (setq P (if (= (gip:g s "brand") "abb") "ab_" "ch_"))
     (setq n (cond ((= k "in") (if is3 (if (= (length (gip:g d "poles")) 4) "a4" "a3") "a2"))
                   ((= k "a1") "a1") ((= k "a3") "a3") ((= k "dif") "dif") ((= k "dif4") "dif4") ((= k "rcd") (if (= (gip:g d "w") 4) "rcd4" "rcd2"))
                   ((= k "fire") (if (= P "ab_") (if is3 "fire4" "fire2") (if is3 "rcd4" "rcd2")))
                   (T nil)))
     (if (and n (assoc (strcat P n) *gip:st-term*)) (strcat P n) nil))
    ((= (gip:g s "brand") "dekraft")
     (cond ((= k "in") (if is3 (if (= (length (gip:g d "poles")) 4) "dk_a4" "dk_a3") "dk_a2"))
           ((= k "a1") "dk_a1") ((= k "a3") "dk_a3") ((= k "dif") "dk_dif") ((= k "dif4") "dk_dif4")
           ((= k "rcd") (if (= (gip:g d "w") 4) "dk_rcd4" "dk_rcd2")) ((= k "fire") (if is3 "dk_rcd4" "dk_rcd2")) (T nil)))
    (T nil)))

;; имя блока аппарата на монтажной схеме
(defun gip:mblock (d s is3 / st k)
  (setq st (gip:g d "st") k (gip:g d "kind"))
  (cond (st (strcat "GIPM_" st))
        ((= k "xb") (strcat "GIPM_G_xb_" (itoa (gip:g d "w"))))
        ((member (gip:g s "brand") '("iek" "chint" "abb" "dekraft"))
         (strcat "GIPM_G_" (gip:g s "brand") "_" (if (and (= k "rcd") (= (gip:g d "w") 4)) "fire" k) "_" (itoa (gip:g d "w"))))
        (T (strcat "GIPM_G_iek_" k "_" (itoa (gip:g d "w"))))))

(defun gip:rating (d) (if (member (gip:g d "kind") '("rcd" "fire")) (strcat (itoa (gip:g d "In")) "A") (strcat "C" (itoa (gip:g d "In")))))

;; клемма аппарата относительно левого верхнего угла
(defun gip:term (d side pole / st tr lst t1 kx arr i)
  (setq st (gip:g d "st"))
  (if (and st (setq tr (cdr (assoc st *gip:st-term*))))
    (progn
      (setq lst (if (= side "top") (cadr tr) (caddr tr)))
      (setq t1 (cdr (assoc pole lst)))
      (if (null t1) (setq t1 (cdr (car lst))))
      (setq kx (/ (* (gip:g d "w") *gip:MW*) (cdr (assoc st *gip:st-vbw*))))
      (list (* (car t1) kx) (cadr t1)))
    (progn
      (setq arr (if (= side "top") (gip:g d "poles") (gip:g d "bot")))
      (setq i (gip:index pole arr)) (if (null i) (setq i 0))
      (list (/ (* (+ i 0.5) (gip:g d "w") *gip:MW*) (max 1 (length arr))) (if (= side "top") 22.0 (- *gip:GH* 22.0))))))

(defun gip:net (d pole is3)
  (cond ((member pole '("N" "A2")) "N") ((= pole "A1") "CTL")
        ((member pole '("L" "Lo")) (if is3 (gip:gn d "phase" "L1") "L")) (T pole)))
;; гребёнка: тип по аппарату (1P, 2P — однополюсные с N, 3P, 4P); фазы однополюсных проверяются при сборке участка
(defun gip:comb-key (d / k)
  (setq k (gip:g d "kind"))
  (cond ((= k "a1") "1P") ((= k "dif") "2P") ((= k "a3") "3P") ((= k "dif4") "4P") (T nil)))
(defun gip:ph-next (p) (cdr (assoc p '(("L1" . "L2") ("L2" . "L3") ("L3" . "L1")))))
;; можно ли продолжить участок гребёнки аппаратом d: одна фаза подряд (однофазная гребёнка)
;; или L1 → L2 → L3 → L1 (трёхфазная гребёнка)
(defun gip:comb-join (run d / dl p q mode)
  (setq dl (last (gip:g run "devs")) p (gip:gn dl "phase" "L") q (gip:gn d "phase" "L") mode (gip:g run "mode"))
  (cond ((not (member (gip:g run "key") '("1P" "2P"))) "fix")
        ((and (/= mode "cyc") (= p q)) "same")
        ((and (/= mode "same") (= (gip:ph-next p) q)) "cyc")
        (T nil)))

;; ---------------------------------------------------------------- преобразование координат pt -> модель
(defun gip:X (x) (+ (car *gip:mo*) (* x (caddr *gip:mo*))))
(defun gip:Y (y) (- (cadr *gip:mo*) (* y (caddr *gip:mo*))))
(defun gip:K (v) (* v (caddr *gip:mo*)))

;; ---------------------------------------------------------------- примитивы монтажной схемы
(setq *gip:mlay* $S163)
(defun gip:aci (tc / r g b)
  (setq r (/ tc 65536) g (rem (/ tc 256) 256) b (rem tc 256))
  (cond ((and (> r 235) (> g 235) (> b 235)) 7)
        ((< (+ r g b) 90) 7)
        ((and (> r 200) (> g 200) (< b 80)) 2)
        ((and (> r 180) (< g 90) (< b 90)) 1)
        ((and (> r 200) (> g 100) (< g 180) (< b 60)) 30)
        ((and (< r 80) (> g 120) (< b 100)) 3)
        ((and (< r 80) (> b 150)) 5)
        ((and (> r 100) (< r 160) (< g 90) (< b 60)) 34)
        ((> (+ r g b) 600) 9)
        ((> (+ r g b) 400) 8)
        (T 8)))
(defun gip:ent-head (typ tc / l)
  (setq l (list (cons 0 typ) '(100 . "AcDbEntity") (cons 8 *gip:mlay*)))
  (if tc (setq l (append l (list (cons 62 (gip:aci tc)) (cons 420 tc)))))
  l)

;; полилиния по точкам pt (список (x y)), bulges — список той же длины или nil
(defun gip:mpoly (pts closed tc w bul / l i)
  (setq l (append (gip:ent-head "LWPOLYLINE" tc)
                  (list '(100 . "AcDbPolyline") (cons 90 (length pts)) (cons 70 (if closed 1 0)) (cons 43 (gip:K w)))))
  (setq i 0)
  (foreach p pts
    (setq l (append l (list (list 10 (gip:X (car p)) (gip:Y (cadr p))))))
    (if (and bul (/= (nth i bul) 0.0)) (setq l (append l (list (cons 42 (nth i bul))))))
    (setq i (1+ i)))
  (gip:mk l *gip:tag*))

;; заливка: полный набор кодов, как у штриховок из файлов ГИП (их AutoCAD создаёт), иначе — через ActiveX
(defun gip:mhatch (pts tc / l e)
  (setq l (append (gip:ent-head "HATCH" tc)
                  (list '(100 . "AcDbHatch") '(10 0.0 0.0 0.0) '(210 0.0 0.0 1.0) '(2 . "SOLID") '(70 . 1) '(71 . 0) '(91 . 1)
                        '(92 . 7) '(72 . 1) '(73 . 1) (cons 93 (length pts)))))
  (foreach p pts (setq l (append l (list (list 10 (gip:X (car p)) (gip:Y (cadr p)) 0.0) '(42 . 0.0)))))
  (setq l (append l (list '(97 . 0) '(75 . 0) '(76 . 1) '(47 . 1.0) '(98 . 1) (list 10 (gip:X (car (car pts))) (gip:Y (cadr (car pts))) 0.0)
                          '(450 . 0) '(451 . 0) '(460 . 0.0) '(461 . 0.0) '(452 . 0) '(462 . 0.0) '(453 . 0) '(470 . ""))))
  (setq e (entmakex (append l (gip:tag-list *gip:tag*))))
  (if (null e) (setq e (gip:mhatch-ax pts tc)))
  e)
(defun gip:mhatch-ax (pts tc / l pl o h arr r e)
  (setq l (list '(0 . "LWPOLYLINE") '(100 . "AcDbEntity") (cons 8 *gip:mlay*) '(100 . "AcDbPolyline") (cons 90 (length pts)) '(70 . 1)))
  (foreach p pts (setq l (append l (list (list 10 (gip:X (car p)) (gip:Y (cadr p)))))))
  (if (setq pl (entmakex l))
    (progn
      (setq o (vlax-ename->vla-object pl))
      (setq h (vl-catch-all-apply 'vla-addhatch (list (gip:ms) 1 "SOLID" :vlax-false)))
      (if (not (vl-catch-all-error-p h))
        (progn
          (setq arr (vlax-make-safearray vlax-vbObject '(0 . 0)))
          (vlax-safearray-fill arr (list o))
          (setq r (vl-catch-all-apply 'vla-appendouterloop (list h (vlax-make-variant arr))))
          (if (vl-catch-all-error-p r)
            (progn (vla-delete h) (setq h nil))
            (progn
              (vl-catch-all-apply 'vla-evaluate (list h))
              (vla-put-layer h *gip:mlay*)
              (vla-put-color h (gip:aci tc))
              (setq e (vlax-vla-object->ename h))
              (entmod (append (entget e) (gip:tag-list *gip:tag*))))))
        (setq h nil))
      (entdel pl)))
  e)

(defun gip:rectpts (x y w h) (list (list x y) (list (+ x w) y) (list (+ x w) (+ y h)) (list x (+ y h))))
;; прямоугольник: заливка fill (или nil) и контур stroke (или nil)
(defun gip:mrect (x y w h fill stroke)
  (if fill (gip:mhatch (gip:rectpts x y w h) fill))
  (if stroke (gip:mpoly (gip:rectpts x y w h) T stroke 0.0 nil)))
;; скруглённый прямоугольник (контур)
(defun gip:mrrect (x y w h r stroke / b)
  (setq b (- (/ (sin (/ pi 8)) (cos (/ pi 8)))))
  (gip:mpoly (list (list (+ x r) y) (list (- (+ x w) r) y) (list (+ x w) (+ y r)) (list (+ x w) (- (+ y h) r))
                   (list (- (+ x w) r) (+ y h)) (list (+ x r) (+ y h)) (list x (- (+ y h) r)) (list x (+ y r)))
             T stroke 0.0 (list 0.0 b 0.0 b 0.0 b 0.0 b)))
(defun gip:mcircle (x y r tc)
  (gip:mk (append (gip:ent-head "CIRCLE" tc) (list '(100 . "AcDbCircle") (list 10 (gip:X x) (gip:Y y) 0.0) (cons 40 (gip:K r)))) *gip:tag*))
(defun gip:mdisk (x y r tc / pts i a)
  (setq pts nil i 0)
  (while (< i 16) (setq a (/ (* i 2 pi) 16) pts (append pts (list (list (+ x (* r (cos a))) (+ y (* r (sin a)))))) i (1+ i)))
  (gip:mhatch pts tc))
(defun gip:mtext (x y fs txt tc ha / h)
  (setq h (gip:K (* fs 0.72)))
  (gip:mk (append (gip:ent-head "TEXT" tc)
                  (list '(100 . "AcDbText") (list 10 (gip:X x) (gip:Y y) 0.0) (cons 40 h) (cons 1 txt) '(7 . "Standard")
                        (cons 72 ha) (list 11 (gip:X x) (gip:Y y) 0.0) '(100 . "AcDbText")))
          *gip:tag*))
(defun gip:mline (x1 y1 x2 y2 tc w) (gip:mpoly (list (list x1 y1) (list x2 y2)) nil tc w nil))

;; провод со скруглёнными углами (дуги-сопряжения через bulge)
(defun gip:mwire (pts net / out bul i p0 p1 p2 l1 l2 r a b d1x d1y d2x d2y cr dt th)
  (setq out (list (car pts)) bul (list 0.0) i 1)
  (while (< i (1- (length pts)))
    (setq p0 (nth (1- i) pts) p1 (nth i pts) p2 (nth (1+ i) pts))
    (setq l1 (distance p0 p1) l2 (distance p1 p2))
    (setq r (min *gip:RC* (/ l1 2.0) (/ l2 2.0)))
    (if (< r 0.5)
      (setq out (append out (list p1)) bul (append bul (list 0.0)))
      (progn
        (setq a (list (+ (car p1) (/ (* (- (car p0) (car p1)) r) l1)) (+ (cadr p1) (/ (* (- (cadr p0) (cadr p1)) r) l1))))
        (setq b (list (+ (car p1) (/ (* (- (car p2) (car p1)) r) l2)) (+ (cadr p1) (/ (* (- (cadr p2) (cadr p1)) r) l2))))
        ;; направление в координатах модели (ось Y вверх): y_модели = -y_pt
        (setq d1x (- (car p1) (car p0)) d1y (- (- (cadr p1) (cadr p0))) d2x (- (car p2) (car p1)) d2y (- (- (cadr p2) (cadr p1))))
        (setq cr (- (* d1x d2y) (* d1y d2x)) dt (+ (* d1x d2x) (* d1y d2y)))
        (setq th (atan (abs cr) dt))
        (setq out (append out (list a b)) bul (append bul (list (* (if (minusp cr) -1.0 1.0) (/ (sin (/ th 4)) (cos (/ th 4)))) 0.0)))))
    (setq i (1+ i)))
  (setq out (append out (list (last pts))) bul (append bul (list 0.0)))
  ;; bulge относится к вершине, с которой начинается дуга
  (gip:mpoly out nil (cdr (assoc net *gip:netc*)) 3.6 (gip:bul-shift bul)))
(defun gip:bul-shift (bul / r i)
  ;; bul: 0 у начала, для каждого скругления — (bulge 0) у точек a b; дуга идёт от a к b => bulge ставим на a
  (setq r nil i 0)
  (foreach v bul (setq r (append r (list v))))
  r)
(defun gip:ferr (x y net up / tc)
  (setq tc (cdr (assoc net *gip:netc*)))
  (gip:mrect (- x 4) (if up (- y 15) (+ y 3)) 8.0 12.0 tc 2236962))

;; бирка: жёлтый прямоугольник с текстом
(defun gip:split-text (s mx ml / words out cur)
  (setq out nil cur "")
  (foreach w (gip:split s " ")
    (if (<= (strlen (gip:trim (strcat cur " " w))) mx)
      (setq cur (gip:trim (strcat cur " " w)))
      (progn (if (/= cur "") (setq out (append out (list cur))))
             (while (> (strlen w) mx) (setq out (append out (list (strcat (substr w 1 (1- mx)) "-"))) w (substr w mx)))
             (setq cur w))))
  (if (/= cur "") (setq out (append out (list cur))))
  (if (> (length out) ml) (setq out (append (gip:take out (1- ml)) (list (strcat (substr (nth (1- ml) out) 1 (max 1 (1- mx))) $S164)))))
  out)
(defun gip:tagbox (x y txt w / lines h i)
  (setq lines (gip:split-text txt (fix (/ (- w 6) 5.6)) 2) h (+ 4 (* (length lines) 11)))
  (gip:mrect x y w h 16776960 8026624)
  (setq i 0)
  (foreach ln lines (gip:mtext (+ x (/ w 2.0)) (+ y 11 (* i 11)) 9.6 ln 1118481 1) (setq i (1+ i))))
(defun gip:loadtag (x y w h d / name per lines i)
  (setq name (gip:g d "name"))
  (if (gip:starts name $S65) (setq name (strcat $S165 (substr name 12))))
  (setq per (max 5 (fix (/ (- w 4) 4.6))) lines (gip:split-text name per 4))
  (gip:mrect x y w (+ 10 (* (length lines) 9.5)) 16776960 8026624)
  (gip:mtext (+ x (/ w 2.0)) (+ y 9) 8.4 (gip:gn d "ref" "") 1194109 1)
  (setq i 0)
  (foreach ln lines (gip:mtext (+ x (/ w 2.0)) (+ y 18.5 (* i 9.5)) 8.2 ln 1118481 1) (setq i (1+ i))))
(defun gip:facetag (x y w d / n ww)
  (setq n (cond ((= (gip:g d "id") "c2") $S166)
                ((= (gip:g d "kind") "in") $S167) ((= (gip:g d "kind") "rn") $S168)
                ((= (gip:g d "kind") "fire") $S169) ((= (gip:g d "kind") "km") $S170)
                ((= (gip:g d "kind") "rcd") (strcat $S171 (itoa (gip:gn d "rcdNo" 0)))) (T nil)))
  (cond ((= (gip:g d "kind") "xb") (gip:tagbox (+ x 4) (+ y (* (gip:g d "h") 0.32)) (strcat (gip:gn d "ref" "") $S172) (- w 8)))
        (n (setq ww (max (- w 4) 44.0)) (gip:tagbox (+ x (/ (- w ww) 2.0)) y (strcat (gip:gn d "ref" "") " " n) ww))))
(defun gip:busshape (x y n col dark / w i cx)
  (setq w (+ (* n 13) 22))
  (gip:mpoly (list (list (+ x 4) (+ y 14)) (list (+ x 10) (- y 2)) (list (- (+ x w) 10) (- y 2)) (list (- (+ x w) 4) (+ y 14))) T 9079434 0.0 nil)
  (gip:mrect x (+ y 14) w 9.0 col dark)
  (setq i 0)
  (while (< i n)
    (setq cx (+ x 15 (* i 13)))
    (gip:mdisk cx (+ y 8) 5.0 14277081) (gip:mcircle cx (+ y 8) 5.0 5592405)
    (gip:mline (- cx 3) (+ y 5) (+ cx 3) (+ y 11) 7829367 0.0) (gip:mline (+ cx 3) (+ y 5) (- cx 3) (+ y 11) 7829367 0.0)
    (setq i (1+ i))))

;; вставка аппарата: блок GIPM_*, атрибуты номинала, метки GIPGEN + GIPDEV(id)
(defun gip:mfill (tpl rt ma In)
  (gip:repl (gip:repl (gip:repl tpl "{R}" (strcat " " rt)) "{M}" (strcat " " ma)) "{I}" (if In (itoa In) "")))
(defun gip:mdev (d x y s is3 / bn obj e rt ma pairs sx vb)
  (setq bn (gip:mblock d s is3) sx (caddr *gip:mo*))
  ;; контактор шире трафарета (ESB40/63 — 3 модуля): растянуть по ширине
  (if (and (= (gip:g d "kind") "km") (gip:g d "st") (setq vb (cdr (assoc (gip:g d "st") *gip:st-vbw*))))
    (setq sx (* sx (/ (* (gip:g d "w") *gip:MW*) vb))))
  (if (not (tblsearch "BLOCK" bn))
    (progn (princ (strcat $S173 bn)) nil)
    (progn
      (setq obj (vla-insertblock (gip:ms) (vlax-3d-point (gip:X x) (gip:Y y) 0.0) bn sx (caddr *gip:mo*) (caddr *gip:mo*) 0.0))
      (vla-put-layer obj (gip:layer *gip:mlay*))
      (setq rt (if (gip:g d "In") (gip:rating d) "") ma (strcat (itoa (gip:gn d "idn" (if (= (gip:g d "kind") "fire") 100 30))) $S97))
      (setq pairs (mapcar '(lambda (p) (cons (car p) (gip:mfill (cdr p) rt ma (gip:g d "In")))) (cdr (assoc bn *gip:mtpl*))))
      (if pairs (gip:set-atts obj pairs))
      (setq e (vlax-vla-object->ename obj))
      (entmod (append (entget e) (list (list -3 (list *gip:app* (cons 1000 *gip:tag*)) (list *gip:dev-app* (cons 1000 (gip:g d "id")))))))
      obj)))

;; ---------------------------------------------------------------- порядок прорисовки
;; таблица порядка прорисовки (ACAD_SORTENTS) пространства/блока owner; mk — создать, если нет
(defun gip:sortents (owner mk / ext st)
  (setq ext (vl-catch-all-apply 'vla-getextensiondictionary (list owner)))
  (if (not (vl-catch-all-error-p ext))
    (progn
      (setq st (vl-catch-all-apply 'vla-getobject (list ext "ACAD_SORTENTS")))
      (if (and (vl-catch-all-error-p st) mk) (setq st (vl-catch-all-apply 'vla-addobject (list ext "ACAD_SORTENTS" "AcDbSortentsTable"))))
      (if (not (vl-catch-all-error-p st)) st))))
;; переместить объекты (enames) на задний (bottom=T) или передний план в owner
(defun gip:draworder (owner enames bottom / st objs arr)
  (setq objs (vl-remove nil (mapcar '(lambda (e) (if (and e (entget e)) (vlax-ename->vla-object e))) enames)))
  (if (and objs (setq st (gip:sortents owner T)))
    (progn
      (setq arr (vlax-make-safearray vlax-vbObject (cons 0 (1- (length objs)))))
      (vlax-safearray-fill arr objs)
      (vl-catch-all-apply (if bottom 'vla-movetobottom 'vla-movetotop) (list st arr)))))
;; объекты, созданные после mark (entlast до рисования)
(defun gip:ents-after (mark / e r)
  (setq e (if mark (entnext mark) (entnext)) r nil)
  (while e (setq r (cons e r) e (entnext e)))
  (reverse r))
;; блоки аппаратов GIPM_* из прежних шаблонов: надписи шли раньше заливок (DEKraft) и закрывались ими —
;; поднять надписи наверх в самом блоке (один раз: у блока появляется таблица порядка прорисовки)
(defun gip:fix-mblocks (/ blks b nm e ed seenT bad late)
  (setq blks (vla-get-blocks (vla-get-activedocument (vlax-get-acad-object))))
  (vlax-for b blks
    (setq nm (vla-get-name b))
    (if (and (wcmatch nm "GIPM_*") (null (gip:sortents b nil)))
      (progn
        (setq e (cdr (assoc -2 (tblsearch "BLOCK" nm))) seenT nil bad nil late nil)
        (while e
          (setq ed (entget e))
          (cond ((= (cdr (assoc 0 ed)) "HATCH") (if seenT (setq bad T)))
                ((member (cdr (assoc 0 ed)) '("TEXT" "MTEXT" "ATTDEF")) (setq seenT T late (cons e late))))
          (setq e (entnext e)))
        ;; заливка идёт после надписи — надписи наверх
        (if bad (gip:draworder b (reverse late) nil))))))

;; ---------------------------------------------------------------- построение монтажной схемы
(defun gip:montage (S BRD Fm / mark0 backs box tall is3 TAGH COMB rails all NR ri acc i d runs cur k jm seen dd chain CONN buses busOrder inD xb fire km c2 rns
                     down INN-k use used ph rs net src g w rn xbSlot lanes trunks TL TR x0 SWD y chY railC hasTag maxH h busY SH bx b nl inc
                     peN peW peX SWX swPts hasSw e PA B2 pts l ya yb xt ly xr ca cb XEXT xa xbx mid ty tx sc BW BH)
  (setq is3 (= (gip:g S "phases") 3) TAGH 50.0 COMB 16.0)
  ;; аппараты: рейка, индекс, смещение, трафарет, высота
  (setq rails nil ri 0)
  (foreach r (gip:g BRD "rails")
    (setq acc 0 i 0 cur nil)
    (foreach d r
      (setq d (gip:s d "rail" ri) d (gip:s d "idx" i) d (gip:s d "xo" (* acc *gip:MW*)))
      (setq d (gip:s d "st" (gip:stencil d S is3)))
      (setq d (gip:s d "h" (if (gip:g d "st") (cadr (assoc (gip:g d "st") *gip:st-term*)) *gip:GH*)))
      (setq acc (+ acc (gip:g d "w")) i (1+ i) cur (append cur (list d))))
    (setq rails (append rails (list cur)) ri (1+ ri)))
  (setq all (apply 'append rails) NR (length rails))
  (setq *gip:mdevs* all)
  (defun gip:m-by (id) (vl-some '(lambda (d) (if (= (gip:g d "id") id) d)) all))
  ;; гребёнки
  (setq runs nil)
  (foreach r rails
    (setq cur nil)
    (foreach d r
      (setq k (gip:comb-key d))
      (if (and k cur (= (gip:g cur "key") k) (= (gip:g cur "feed") (gip:g d "feed")) (setq jm (gip:comb-join cur d)))
        (setq cur (gip:s (gip:s cur "devs" (append (gip:g cur "devs") (list d))) "mode" jm))
        (progn (if cur (setq runs (append runs (list cur))))
               (setq cur (list (cons "key" k) (cons "feed" (gip:g d "feed")) (cons "devs" (list d)) (cons "mode" nil))))))
    (if cur (setq runs (append runs (list cur)))))
  ;; соединения: элементы связи — (dev-id side pole) | ("ext" k) | ("bus" key) | ("sw" n)
  (setq CONN nil buses (list (cons "main" $S174)) busOrder (list "main"))
  (setq inD (gip:m-by "in") xb (gip:m-by "xb") fire (gip:m-by "fire") km (gip:m-by "km") c2 (gip:m-by "c2"))
  (setq rns (vl-remove-if-not '(lambda (d) (= (gip:g d "kind") "rn")) all))
  (setq INN-k 0)
  (defun gip:m-inn () (if (member "N" (gip:g inD "poles")) (list "in" "bot" "N") (progn (setq INN-k (1+ INN-k)) (list "ext" (1- INN-k)))))
  ;; ввод -> (реле) -> УЗО 100 мА -> кросс-модуль; без кросс-модуля группы питаются от последнего аппарата цепочки, N — от шины
  (setq down (cond (fire (list "fire" "top")) (xb (list "xb" "bot")) (T nil)))
  (defun gip:m-d2 (p) (list (car down) (cadr down) p))
  (defun gip:m-cadd (a b net) (setq CONN (append CONN (list (list a b net)))))
  (if rns
    (progn
      (setq i 0)
      (foreach rn rns
        (setq ph (if is3 (gip:g rn "phase") "L") rs (if (gip:g rn "st") "top" "bot"))
        (gip:m-cadd (list "in" "bot" ph) (list (gip:g rn "id") rs "L") ph)
        (gip:m-cadd (if (= i 0) (gip:m-inn) (list (gip:g (nth (1- i) rns) "id") rs "N")) (list (gip:g rn "id") rs "N") "N")
        (if down (gip:m-cadd (list (gip:g rn "id") "bot" "Lo") (gip:m-d2 ph) ph))
        (setq i (1+ i))))
    (if down (foreach ph (if is3 '("L1" "L2" "L3") '("L")) (gip:m-cadd (list "in" "bot" ph) (gip:m-d2 ph) ph))))
  (gip:m-cadd (gip:m-inn) (if down (gip:m-d2 "N") (list "bus" "main")) "N")
  (if fire
    (if xb
      (foreach p (gip:g fire "poles") (gip:m-cadd (list "fire" "bot" p) (list "xb" "bot" p) (gip:net fire p is3)))
      (gip:m-cadd (list "fire" "bot" "N") (list "bus" "main") "N")))
  (if xb (gip:m-cadd (list "xb" "bot" "N") (list "bus" "main") "N"))
  ;; источник фазы net для групп «от ввода»
  (defun gip:m-src (net d / rn)
    (cond (xb (list "xb" (if (= (gip:g d "rail") (gip:g xb "rail")) "top" "bot") (if (= net "N") "N" (if is3 net "L"))))
          ((= net "N") (list "bus" "main"))
          (fire (list "fire" "bot" (if is3 net "L")))
          ((and rns (setq rn (if is3 (vl-some '(lambda (r) (if (= (gip:g r "phase") net) r)) rns) (car rns)))) (list (gip:g rn "id") "bot" "Lo"))
          (T (list "in" "bot" (if is3 net "L")))))
  ;; подвод к аппарату d (полюс p) участка гребёнки; без кросс-модуля — шлейфом от предыдущего аппарата той же фазы
  ;; (не больше двух проводов в клемме)
  (setq chain nil)
  (defun gip:m-feed (d p / net src e)
    (setq net (gip:net d p is3) src (gip:g d "feed") e (list (gip:g d "id") "top" p))
    (cond ((= src "src")
           (gip:m-cadd (if (and (null xb) (gip:g chain net)) (gip:g chain net) (gip:m-src net d)) e net)
           (if (null xb) (setq chain (gip:s chain net e))))
          ((and (= src "km") km) (if (/= net "N") (gip:m-cadd (list "km" "bot" (if is3 net "L")) (list (gip:g d "id") "top" p) net)))
          ((and src (gip:starts src "rcd")) (if (and (gip:m-by src) (/= net "N")) (gip:m-cadd (list src "bot" (if (= (gip:g (gip:m-by src) "w") 4) net "L")) (list (gip:g d "id") "top" p) net)))))
  (foreach rn runs
    (setq d (car (gip:g rn "devs")))
    (if (not (member (gip:g d "kind") '("in" "rn" "fire" "xb")))
      (progn
        (if (= (gip:g rn "mode") "cyc")
          ;; трёхфазная гребёнка: каждая фаза — к первому аппарату этой фазы, N — один раз
          (progn
            (setq seen nil)
            (foreach dd (gip:g rn "devs")
              (if (not (member (gip:g dd "phase") seen))
                (progn (setq seen (cons (gip:g dd "phase") seen)) (gip:m-feed dd "L"))))
            (if (member "N" (gip:g d "poles")) (gip:m-feed d "N")))
          (foreach p (gip:g d "poles") (if (/= p "A1") (gip:m-feed d p))))
        (if (= (gip:g d "kind") "rcd")
          (progn (setq k (strcat "rcd" (itoa (gip:g d "rcdNo"))))
                 (setq buses (append buses (list (cons k (strcat "N " (gip:g d "ref"))))) busOrder (append busOrder (list k)))
                 (gip:m-cadd (list (gip:g d "id") "bot" "N") (list "bus" k) "N"))))))
  (setq hasSw (and km c2))
  (if hasSw
    (progn (gip:m-cadd (list "c2" "bot" "L") (list "sw" 1) (if is3 "L1" "L"))
           (gip:m-cadd (list "sw" 2) (list "km" "top" "A1") "CTL")
           (gip:m-cadd (list "km" "bot" "A2") (list "bus" "main") "N")))
  ;; точки подключения: каждой связи — своя
  (setq use nil)
  (foreach c CONN (foreach e (list (car c) (cadr c))
                 (if (and (not (member (car e) '("ext" "bus" "sw"))) (/= (gip:g (gip:m-by (car e)) "kind") "xb"))
                   (setq use (gip:s use (gip:join e "|") (1+ (gip:gn use (gip:join e "|") 0)))))))
  (setq used nil xbSlot (list (cons "top" 0) (cons "bot" 0)))
  (defun gip:m-endrel (e / d bars bi n cols x kk barH t1 key nn ii)
    (setq d (gip:m-by (car e)))
    (if (= (gip:g d "kind") "xb")
      (progn
        (setq bars (length (gip:g d "poles")) bi (gip:index (caddr e) (gip:g d "poles"))) (if (null bi) (setq bi 0))
        (setq n (gip:g xbSlot (cadr e)) xbSlot (gip:s xbSlot (cadr e) (1+ n)))
        (setq cols (* (gip:g d "w") 3) x (+ 10 (* (rem n cols) (/ (- (* (gip:g d "w") *gip:MW*) 20) (- cols 1)))))
        (setq kk (/ *gip:MW* 36.0) barH (/ (- *gip:GH* (* 70 kk)) bars))
        (list x (+ (* 35 kk) (* bi barH) (/ barH 2.0)) T))
      (progn
        (setq t1 (gip:term d (cadr e) (caddr e)) key (gip:join e "|") nn (gip:gn use key 1) ii (gip:gn used key 0))
        (setq used (gip:s used key (1+ ii)))
        (list (+ (car t1) (if (> nn 1) (* (- ii (/ (- nn 1) 2.0)) 7.0) 0.0)) (cadr t1) nil))))
  (setq CONN (mapcar '(lambda (c / a b) (setq a (car c) b (cadr c))
                     (list (if (member (car a) '("ext" "bus" "sw")) a (append a (list (gip:m-endrel a))))
                           (if (member (car b) '("ext" "bus" "sw")) b (append b (list (gip:m-endrel b))))
                           (caddr c))) CONN))
  ;; каналы
  (defun gip:m-chof (e) (cond ((= (car e) "ext") 0) ((= (car e) "bus") NR) ((= (car e) "sw") nil)
                        ((= (cadr e) "top") (gip:g (gip:m-by (car e)) "rail")) (T (1+ (gip:g (gip:m-by (car e)) "rail")))))
  (setq lanes (mapcar '(lambda (x) 0) (gip:range (1+ NR))) trunks (list (cons "L" 0) (cons "R" 0)))
  (defun gip:m-lane (ch / v) (setq v (nth ch lanes) lanes (append (gip:take lanes ch) (list (1+ v)) (gip:drop lanes (1+ ch)))) v)
  (setq XEXT (+ (gip:g inD "xo") (* (gip:g inD "w") *gip:MW*) 12))
  (defun gip:m-ex (e) (cond ((= (car e) "bus") nil) ((= (car e) "ext") (+ XEXT (* (cadr e) 8))) (T (+ (gip:g (gip:m-by (car e)) "xo") (car (cadddr e))))))
  (setq CONN (mapcar '(lambda (c / a b ca cb sw e2 la lb side tk xa xbx mid)
                     (setq a (car c) b (cadr c))
                     (if (or (= (car a) "sw") (= (car b) "sw"))
                       (progn (setq e2 (if (= (car a) "sw") b a) ca (gip:m-chof e2))
                              (append c (list (list "sw" ca (gip:m-lane ca) (if (= (car a) "sw") (cadr a) (cadr b))))))
                       (progn
                         (setq ca (gip:m-chof a) cb (gip:m-chof b))
                         (if (= ca cb)
                           (append c (list (list "same" ca (gip:m-lane ca))))
                           (progn
                             (setq la (gip:m-lane ca) lb (gip:m-lane cb) xa (gip:m-ex a) xbx (gip:m-ex b))
                             (setq mid (cond ((null xa) xbx) ((null xbx) xa) (T (/ (+ xa xbx) 2.0))))
                             (setq side (if (< mid (/ (* (gip:g S "railW") *gip:MW*) 2.0)) "L" "R"))
                             (setq tk (gip:g trunks side) trunks (gip:s trunks side (1+ tk)))
                             (append c (list (list "cross" ca cb la lb side tk)))))))) CONN))
  ;; геометрия
  (setq TL (+ 40 (* (gip:g trunks "L") *gip:LANE*)) TR (+ 46 (* (gip:g trunks "R") *gip:LANE*) (if hasSw (+ (* 2 *gip:LANE*) 6) 0)))
  (setq x0 TL SWD (+ TL (* (gip:g S "railW") *gip:MW*) TR))
  (setq y 92.0 chY nil railC nil hasTag nil maxH nil)
  (foreach r rails
    (setq hasTag (append hasTag (list (vl-some '(lambda (d) (gip:g d "line")) r))))
    (setq maxH (append maxH (list (apply 'max (cons *gip:GH* (mapcar '(lambda (d) (gip:g d "h")) r)))))))
  (setq k 0)
  (while (<= k NR)
    (setq h (max 34 (+ 22 (* (nth k lanes) *gip:LANE*))))
    (setq chY (append chY (list (list y h))) y (+ y h))
    (if (< k NR)
      (progn (setq y (+ y COMB) railC (append railC (list (+ y (/ (nth k maxH) 2.0)))))
             (setq y (+ y (nth k maxH) (if (nth k hasTag) (+ TAGH 10) 12)))))
    (setq k (1+ k)))
  (setq busY (+ y 30) SH (+ busY 70))
  ;; масштаб под лист: узкий щит — слева от штампа во всю высоту, широкий — над штампом
  (setq tall (< (/ (+ SWD (if hasSw 150.0 20.0)) SH) (/ 10250.0 13530.0)))
  (setq box (if tall (list (- (car Fm) 19700.0) (+ (cadr Fm) 420.0) (- (car Fm) 9450.0) (+ (cadr Fm) 13950.0))
                     (list (- (car Fm) 19800.0) (+ (cadr Fm) 3050.0) (- (car Fm) 450.0) (+ (cadr Fm) 13950.0))))
  (setq BW (- (caddr box) (car box)) BH (- (cadddr box) (cadr box)))
  (setq sc (min (/ BW (+ SWD (if hasSw 150 20))) (/ BH SH)))
  (setq *gip:mo* (list (+ (car box) (/ (- BW (* (+ SWD (if hasSw 150 20)) sc)) 2.0)) (- (cadddr box) (/ (- BH (* SH sc)) 2.0)) sc))
  (setq *gip:mgeo* (list (cons "mo" *gip:mo*) (cons "x0" x0) (cons "railC" railC) (cons "railW" (gip:g S "railW")) (cons "R" NR)))
  (defun gip:m-laney (ch i) (+ (car (nth ch chY)) 16 (* i *gip:LANE*)))
  (defun gip:m-devtop (d) (- (nth (gip:g d "rail") railC) (/ (gip:g d "h") 2.0)))
  (defun gip:m-p (e / d)
    (cond ((= (car e) "ext") (list (+ x0 (gip:g inD "xo") (* (gip:g inD "w") *gip:MW*) 12 (* (cadr e) 8)) 4.0 "ext"))
          ((= (car e) "bus") (list (gip:m-busterm (cadr e)) (+ busY 4) "bus"))
          (T (setq d (gip:m-by (car e)))
             (list (+ x0 (gip:g d "xo") (car (cadddr e))) (+ (gip:m-devtop d) (cadr (cadddr e))) (cadr e) (caddr (cadddr e))))))
  ;; шины N
  (setq bx (+ x0 4) b nil)
  (setq buses (mapcar '(lambda (k / nm nl inc n w)
                         (setq nm (cdr (assoc k buses)))
                         (setq nl (if (= k "main")
                                    (length (vl-remove-if-not '(lambda (d) (and (gip:g d "line") (not (gip:g d "rcdNo")) (member (gip:g d "kind") '("a1" "a3")))) all))
                                    (length (vl-remove-if-not '(lambda (d) (and (= (strcat "rcd" (itoa (gip:gn d "rcdNo" 0))) k) (gip:g d "line"))) all))))
                         (setq inc (length (vl-remove-if-not '(lambda (c) (and (= (car (cadr c)) "bus") (= (cadr (cadr c)) k))) CONN)))
                         (setq n (max 6 (+ nl inc 1)) w (+ (* n 13) 22))
                         (setq b (list k nm bx n w 0) bx (+ bx w 16))
                         b) busOrder))
  (defun gip:m-busterm (k / bb x)
    (setq bb (assoc k buses) x (+ (nth 2 bb) 15 (* (nth 5 bb) 13)))
    (setq buses (subst (append (gip:take bb 5) (list (1+ (nth 5 bb)))) bb buses))
    x)
  ;; ---- рисование
  (gip:layer *gip:mlay*)
  (vl-catch-all-apply 'gip:fix-mblocks nil)
  (setq mark0 (entlast))
  (gip:mrrect 2.0 2.0 (- SWD 4) (- SH 4) 16.0 9079434)
  (gip:mrrect 22.0 22.0 (- SWD 44) (- SH 44) 8.0 10132122)
  (foreach p (list (list 34.0 34.0) (list (- SWD 34) 34.0) (list 34.0 (- SH 34)) (list (- SWD 34) (- SH 34)))
    (gip:mcircle (car p) (cadr p) 7.0 7829367) (gip:mcircle (car p) (cadr p) 3.0 7829367))
  (foreach c railC
    (gip:mrect (- x0 14) (- c 50) (+ (* (gip:g S "railW") *gip:MW*) 28) 100.0 16053492 11908533)
    (gip:mrect (- x0 14) (- c 17) (+ (* (gip:g S "railW") *gip:MW*) 28) 34.0 14474460 10132122))
  ;; корпус и DIN-рейки — на задний план (под аппараты), независимо от прежних DRAWORDER в чертеже
  (setq backs (gip:ents-after mark0))
  ;; шина PE
  (setq peN (min 26 (max 12 (+ 4 (length (vl-remove-if-not '(lambda (d) (gip:g d "line")) all))))))
  (setq peW (+ (* peN 13) 22) peX (max x0 (- SWD TR peW)))
  (gip:busshape peX 40.0 peN 9291327 6066978)
  (gip:tagbox (- (+ peX (/ peW 2.0)) 56) 72.0 $S175 112.0)
  ;; аппараты
  (foreach d all (gip:mdev d (+ x0 (gip:g d "xo")) (gip:m-devtop d) S is3))
  ;; гребёнки
  (foreach rn runs
    (if (> (length (gip:g rn "devs")) 1)
      (progn
        (setq d (car (gip:g rn "devs")) e (last (gip:g rn "devs")))
        (setq xa (+ x0 (gip:g d "xo") 3) xt (- (+ x0 (gip:g e "xo") (* (gip:g e "w") *gip:MW*)) 3))
        (setq ty (- (+ (gip:m-devtop d) (apply 'min (mapcar '(lambda (p) (cadr (gip:term d "top" p))) (gip:g d "poles")))) COMB 4))
        (gip:mrect xa ty (- xt xa) 8.0 12434877 7039851)
        (foreach dd (gip:g rn "devs")
          (foreach p (gip:g dd "poles")
            (if (/= p "A1")
              (progn (setq pts (gip:term dd "top" p))
                     (gip:mrect (- (+ x0 (gip:g dd "xo") (car pts)) 2.5) (+ ty 8) 5.0 (- (+ (gip:m-devtop dd) (cadr pts)) ty 8) 12434877 7039851)))))
        (gip:mtext (+ xa 2) (- ty 3) 11.0 (if (= (gip:g rn "mode") "cyc") (if (= (gip:g rn "key") "2P") $S176 $S177) (gip:g rn "key")) 1118481 0))))
  ;; ввод
  (foreach p (gip:g inD "poles")
    (setq pts (gip:term inD "top" p) xa (+ x0 (gip:g inD "xo") (car pts)) ya (+ (gip:m-devtop inD) (cadr pts)))
    (gip:mwire (list (list xa 4.0) (list xa ya)) (gip:net inD p is3))
    (gip:ferr xa ya (gip:net inD p is3) T))
  (gip:tagbox (- (+ x0 (gip:g inD "xo")) 4) 40.0 (if is3 $S178 $S179) 86.0)
  ;; провода
  (setq SWX (+ (- SWD TR) (* (gip:g trunks "R") *gip:LANE*) 30) swPts nil)
  (foreach c CONN
    (setq net (caddr c) g (nth 3 c))
    (cond
      ((= (car g) "sw")
       (setq e (if (= (car (car c)) "sw") (cadr c) (car c)) PA (gip:m-p e) ly (gip:m-laney (cadr g) (caddr g)) xr (+ SWX (* (1- (cadddr g)) *gip:LANE*)))
       (setq swPts (gip:s swPts (itoa (cadddr g)) (list xr ly)))
       (gip:mwire (list (list (car PA) (cadr PA)) (list (car PA) ly) (list xr ly)) net)
       (gip:end-mark PA net))
      (T
       (setq PA (gip:m-p (car c)) B2 (gip:m-p (cadr c)))
       (if (= (car g) "same")
         (progn (setq l (gip:m-laney (cadr g) (caddr g)))
                (setq pts (list (list (car PA) (cadr PA)) (list (car PA) l) (list (car B2) l) (list (car B2) (cadr B2)))))
         (progn (setq ya (gip:m-laney (nth 1 g) (nth 3 g)) yb (gip:m-laney (nth 2 g) (nth 4 g)))
                (setq xt (if (= (nth 5 g) "L") (- TL 16 (* (nth 6 g) *gip:LANE*)) (+ x0 (* (gip:g S "railW") *gip:MW*) 20 (* (nth 6 g) *gip:LANE*))))
                (setq pts (list (list (car PA) (cadr PA)) (list (car PA) ya) (list xt ya) (list xt yb) (list (car B2) yb) (list (car B2) (cadr B2))))))
       (gip:mwire pts net)
       (gip:end-mark PA net) (gip:end-mark B2 net))))
  (if (and (gip:g swPts "1") (gip:g swPts "2"))
    (progn
      (setq PA (gip:g swPts "1") B2 (gip:g swPts "2"))
      (setq ty (+ (min (cadr PA) (cadr B2)) (/ (abs (- (cadr PA) (cadr B2))) 2.0)) tx (+ SWD 8))
      (gip:mwire (list PA (list (+ tx 30) (cadr PA)) (list (+ tx 30) ty)) (if is3 "L1" "L"))
      (gip:mwire (list B2 (list (+ tx 44) (cadr B2)) (list (+ tx 44) ty)) "CTL")
      (gip:tagbox tx (- ty 2) $S180 110.0)))
  ;; шины N
  (foreach bb buses
    (gip:busshape (nth 2 bb) busY (max (nth 3 bb) (1+ (nth 5 bb))) 2730721 1732520)
    (gip:tagbox (- (+ (nth 2 bb) (/ (nth 4 bb) 2.0)) 44) (+ busY 34) (nth 1 bb) 88.0))
  ;; бирки
  (foreach d all
    (setq w (* (gip:g d "w") *gip:MW*))
    (if (gip:g d "line")
      (gip:loadtag (+ x0 (gip:g d "xo") 2) (+ (nth (gip:g d "rail") railC) (/ (nth (gip:g d "rail") maxH) 2.0) 6) (- w 4) TAGH d)
      (gip:facetag (+ x0 (gip:g d "xo")) (+ (gip:m-devtop d) (* (gip:g d "h") 0.56)) w d)))
  (vl-catch-all-apply 'gip:draworder (list (gip:ms) backs T))
  all)

(defun gip:end-mark (p net)
  (cond ((= (caddr p) "ext") nil)
        ((= (caddr p) "bus") (gip:ferr (car p) (cadr p) net T))
        ((cadddr p) (gip:mdisk (car p) (cadr p) 3.4 16777215) (gip:mcircle (car p) (cadr p) 3.4 3355443))
        (T (gip:ferr (car p) (cadr p) net (= (caddr p) "top")))))
;;; ============================================================================
;;; Спецификация (форма ГИП): щитовое оборудование, оборудование по планам,
;;; материалы, кабельная продукция с длинами по площади квартиры
;;; ============================================================================

;; строка: (("name" . ..) ("type" . ..) ("maker" . ..) ("unit" . ..) ("qty" . ..))
(defun gip:row (name typ maker unit qty)
  (list (cons "name" name) (cons "type" typ) (cons "maker" maker) (cons "unit" unit) (cons "qty" qty)))

(defun gip:spec-board (S BRD b / is3 map order add p pp kk p2 p4 rank k bx)
  (setq is3 (= (gip:g S "phases") 3) map nil order nil)
  (defun gip:sp-add (key r)
    (if (assoc key map)
      (setq map (subst (cons key (gip:s (cdr (assoc key map)) "qty" (1+ (gip:g (cdr (assoc key map)) "qty")))) (assoc key map) map))
      (setq map (append map (list (cons key (gip:s r "qty" 1)))) order (append order (list key)))))
  (setq bx (gip:g BRD "box"))
  (gip:sp-add "box"
    (if bx
      (gip:row (strcat $S181 (if (gip:starts (car bx) "UK") "UK600" "Mistral41F") ", " (itoa (cadr bx)) " "
                       (if (= (cadr bx) 1) $S182 (if (< (cadr bx) 5) $S183 $S184)) ", " (itoa (* (cadr bx) (gip:g S "railW"))) $S185
                       (if (gip:starts (car bx) "UK") "IP30" "IP41") $S186)
               (if (/= (caddr bx) "") (caddr bx) (car bx)) "ABB" $S187 1)
      (gip:row (strcat $S188 (itoa (gip:g BRD "cap")) $S189) "" (gip:g b "name") $S187 1)))
  (foreach d (gip:g BRD "all")
    (setq k (gip:g d "kind"))
    (cond
      ((= k "rn") (gip:sp-add "rn" (gip:row $S190 "VIP-63" "Welrok" $S187 1)))
      ((member k '("in" "a1" "a3"))
       (setq pp (cond ((= k "in") (if is3 (if (= (gip:g S "inPoles") 4) 4 3) 2)) ((= k "a3") 3) (T 1)))
       (setq kk (nth pp '("" "a1" "a2" "a3" "a4")))
       (gip:sp-add (strcat "a" (itoa pp) "_" (gip:pad0 (itoa (gip:g d "In")) 3))
                   (gip:row (strcat $S191 (itoa pp) $S192 (itoa (gip:g d "In")) $S193) (gip:brand-ser b kk (gip:g d "In")) (gip:g b "name") $S187 1)))
      ((member k '("dif" "dif4"))
       (setq p2 (if (= k "dif4") 4 2))
       (gip:sp-add (strcat "d" (itoa p2) "_" (gip:pad0 (itoa (gip:g d "In")) 3) "_" (itoa (gip:gn d "idn" 30)))
                   (gip:row (strcat $S194 (itoa p2) $S192 (itoa (gip:g d "In")) $S195 (itoa (gip:gn d "idn" 30)) $S196) (gip:brand-ser b k (gip:g d "In")) (gip:g b "name") $S187 1)))
      ((= k "rcd")
       (setq p2 (if (= (gip:g d "w") 4) 4 2))
       (gip:sp-add (strcat "r" (itoa p2) "_" (gip:pad0 (itoa (gip:g d "In")) 3) "_" (itoa (gip:gn d "idn" 30)) (gip:gn d "type" "A"))
                   (gip:row (strcat $S197 (itoa p2) $S198 (itoa (gip:g d "In")) "A, " (itoa (gip:gn d "idn" 30)) $S199 (if (= (gip:g d "type") "AC") "AC" "A") $S200)
                            (gip:gn d "model" (gip:fmt-model (gip:g b "rcd2") (gip:g d "In"))) (gip:g b "name") $S187 1)))
      ((= k "fire")
       (setq p4 (if is3 4 2))
       (gip:sp-add (strcat "f" (itoa p4) "_" (gip:pad0 (itoa (gip:g d "In")) 3))
                   (gip:row (strcat $S201 (itoa p4) $S198 (itoa (gip:g d "In")) $S202) (gip:fmt-model (gip:g b (if is3 "fire4" "fire2")) (gip:g d "In")) (gip:g b "name") $S187 1)))
      ((= k "km") (gip:sp-add "km" (gip:row (strcat $S203 (itoa (gip:gn d "kmI" 25)) "A, " (itoa (gip:gn d "kmC" (if is3 4 2))) $S204) (gip:g d "model") (gip:g b "name") $S187 1)))
      ((= k "xb") (gip:sp-add "xb" (gip:row (strcat $S205 (if is3 $S206 $S207) ", 125A") "" "" $S187 1)))))
  (gip:sp-add "nbus" (gip:row $S208 "" "" $S187 1))
  (gip:sp-add "pebus" (gip:row $S209 "" "" $S187 1))
  ;; порядок как в проектах ГИП
  (defun gip:sp-rank (key / c)
    (setq c (substr key 1 1))
    (cond ((= key "box") (list 0 0 0)) ((= key "rn") (list 1 0 0))
          ((and (member c '("a" "d" "r" "f")) (= (substr key 3 1) "_"))
           (list (cdr (assoc c '(("a" . 2) ("d" . 3) ("r" . 4) ("f" . 4)))) (- (atoi (substr key 2 1))) (atoi (substr key 4))))
          (T (list (gip:gn '(("km" . 5) ("xb" . 6) ("nbus" . 7) ("pebus" . 8)) key 9) 0 0))))
  (setq order (gip:msort order '(lambda (x y / a b) (setq a (gip:sp-rank x) b (gip:sp-rank y))
                                    (cond ((/= (car a) (car b)) (< (car a) (car b))) ((/= (cadr a) (cadr b)) (< (cadr a) (cadr b))) (T (< (caddr a) (caddr b)))))))
  (mapcar '(lambda (k) (cdr (assoc k map))) order))

;; оборудование по планам: блоки ГИП на планах (розетки, выключатели, светильники) по «Виду»
(setq *gip:plan-map* $Q210)

(defun gip:plan-counts (sheets / ss i e o nm v cnt r ip boxes)
  ;; считаем только блоки на листах планов (роль plan_*), условные обозначения не трогаем
  (setq cnt nil boxes nil)
  (foreach sh sheets
    (if (gip:starts (gip:g sh "role") "plan_")
      (setq boxes (cons (list (- (car (gip:g sh "F")) *gip:SW*) (cadr (gip:g sh "F")) (car (gip:g sh "F")) (+ (cadr (gip:g sh "F")) *gip:SHH*)) boxes))))
  (if (and boxes (setq ss (ssget "_X" '((0 . "INSERT")))))
    (progn
      (setq i 0)
      (while (< i (sslength ss))
        (setq e (ssname ss i) i (1+ i) ip (cdr (assoc 10 (entget e))))
        (if (and (not (assoc -3 (entget e (list *gip:app*))))
                 (vl-some '(lambda (b) (and (< (car b) (car ip) (caddr b)) (< (cadr b) (cadr ip) (cadddr b)))) boxes))
          (progn
            (setq o (vlax-ename->vla-object e))
            (setq nm (vl-catch-all-apply 'vlax-get (list o 'EffectiveName)))
            (if (and (= (type nm) 'STR) (member nm $Q211))
              (progn
                (setq v nil)
                (foreach p (vlax-invoke o 'GetDynamicBlockProperties)
                  (if (= (vlax-get p 'PropertyName) $S105) (setq v (vlax-get p 'Value))))
                (if (setq r (assoc v *gip:plan-map*))
                  (setq cnt (gip:s cnt v (1+ (gip:gn cnt v 0))))))))))))
  cnt)

(defun gip:bath-count (S / n)
  (setq n 0)
  (foreach l (gip:g S "light")
    (if (or (gip:has (gip:lower l) $S121) (gip:has (gip:lower l) $S122) (gip:has (gip:lower l) $S123)) (setq n (1+ n))))
  (max n 1))

(defun gip:round5 (x) (* 5 (gip:ceil (/ x 5.0))))

;; все строки спецификации: список секций (номер название строки)
(defun gip:spec-sections (S BRD sheets / b sec1 cnt sec2 r sw sk boxes cab cabs mats bath sv area kup pe6 pe25 d20 d16 d25 d32 c)
  (setq b *gip:b* area (gip:gn S "area" 50.0) bath (gip:bath-count S) kup (gip:g S "kup"))
  (setq sec1 (gip:spec-board S BRD b))
  ;; оборудование по планам
  (setq cnt (gip:plan-counts sheets) sec2 nil sw 0)
  (foreach m *gip:plan-map*
    (if (setq c (gip:g cnt (car m)))
      (progn
        (setq sec2 (append sec2 (list (if (= (caddr m) "c")
                                        (gip:row (cadr m) $S212 $S212 $S187 c)
                                        (gip:row (cadr m) "" "Legrand" $S187 c)))))
        (if (= (caddr m) "s") (setq sw (+ sw c))))))
  (if (> sw 0) (setq sec2 (append sec2 (list (gip:row $S213 "" "Legrand" $S187 sw)))))
  ;; кабели и трубы по длинам линий
  (setq cabs nil d16 0 d20 0 d25 0 d32 0)
  (foreach l (vl-remove-if '(lambda (l) (or (gip:g l "reserve") (= (gip:gn l "cable" "") "") (<= (gip:gn l "len" 0) 0))) (gip:g BRD "lines"))
    (setq c (gip:repl (gip:g l "cable") $S94 $S214))
    (setq cabs (gip:s cabs c (+ (gip:gn cabs c 0) (gip:g l "len"))))
    (setq sv (gip:conduit (gip:g l "cable")))
    (cond ((= sv $S117) (setq d16 (+ d16 (gip:g l "len")))) ((= sv $S118) (setq d20 (+ d20 (gip:g l "len"))))
          ((= sv $S119) (setq d25 (+ d25 (gip:g l "len")))) (T (setq d32 (+ d32 (gip:g l "len"))))))
  (setq cabs (gip:msort cabs '(lambda (a b) (< (gip:cab-key (car a)) (gip:cab-key (car b))))))
  (setq pe6 (if kup (* bath (gip:ceil (+ 1.5 (* 0.45 (sqrt area))))) 0) pe25 (if kup (* bath 15) 0))
  (setq mats nil)
  (foreach q (list (list d16 "16" "0616" "011631") (list d20 "20" "0620" "012031") (list d25 "25" "0625" "012531") (list d32 "32" "0632" "013231"))
    (if (> (car q) 0)
      (setq mats (append mats (list (gip:row (strcat $S215 (cadr q) $S216) (caddr q) $S217 $S187 (gip:round5 (car q)))
                                    (gip:row (strcat $S218 (cadr q) $S216) (cadddr q) $S217 $S219 (gip:round5 (car q))))))))
  (setq mats (append mats (list (gip:row $S220 "" "" $S221 1))))
  (if (> (gip:gn S "floor" 0) 0) (setq mats (append mats (list (gip:row $S222 "" "" $S221 (gip:g S "floor"))))))
  (if kup (setq mats (append mats (list (gip:row $S223 "" $S224 $S187 bath)))))
  (setq cab nil)
  (foreach c cabs (setq cab (append cab (list (gip:row (strcat $S225 (car c) $S226) (gip:gn S "mark" $S98) $S227 $S219 (gip:round5 (cdr c)))))))
  (if kup
    (setq cab (append cab (list (gip:row $S228 $S229 $S227 $S219 pe6)
                                (gip:row $S230 $S229 $S227 $S219 pe25)))))
  (list (list $S231 sec1)
        (if sec2 (list $S232 sec2))
        (list $S233 mats)
        (list $S234 cab)))

(defun gip:cab-key (s / p a b)
  ;; "3х1,5" -> 3001.5 для сортировки
  (setq p (vl-string-search $S214 s))
  (if p (+ (* 1000 (atoi (substr s 1 p))) (atof (gip:repl (substr s (+ p 2)) "," "."))) 0))

;; раскладка спецификации по листам: стр.1 — секции 1–2, далее — 3–4 (как в проектах ГИП)
(setq *gip:spec-rows* 27)
(defun gip:spec-pages (secs / pages cur no)
  (setq pages nil cur nil no 0)
  (defun gip:sp-addsec (sec / rows)
    (setq no (1+ no))
    (setq rows (cons (list (cons "sec" T) (cons "pos" no) (cons "name" (car sec))) (cadr sec)))
    (foreach r rows
      (if (>= (length cur) *gip:spec-rows*) (setq pages (append pages (list cur)) cur nil))
      (setq cur (append cur (list r))))
    (if (< (length cur) *gip:spec-rows*) (setq cur (append cur (list nil)))))
  (foreach sec (vl-remove 'nil (list (nth 0 secs) (nth 1 secs))) (gip:sp-addsec sec))
  (setq pages (append pages (list cur)) cur nil)
  (foreach sec (vl-remove 'nil (list (nth 2 secs) (nth 3 secs))) (gip:sp-addsec sec))
  (if cur (setq pages (append pages (list cur))))
  pages)

;; лист спецификации с правым нижним углом рамки F
(defun gip:spec-sheet (rows F no tot / ri y fx fy)
  (setq fx (car F) fy (cadr F))
  (gip:place "frame" (+ fx -19960.1234209281) (+ fy 10782.4628509109)
    $Q235)
  (gip:place "specpage" fx fy
    $Q236)
  (setq ri 0)
  (repeat *gip:spec-rows*
    (gip:place "specrow" fx (+ fy 13600.0 (* ri -400.0)) nil)
    (setq ri (1+ ri)))
  (setq ri 0)
  (foreach r rows
    (setq y (+ fy 13600.0 (* ri -400.0)))
    (cond
      ((null r) nil)
      ((gip:g r "sec")
       (gip:mt "cell_secpos" (- fx 19460.5) y (itoa (gip:g r "pos")) nil)
       (gip:mt "cell_secname" (- fx 14960.5) y (gip:g r "name") nil))
      (T
       (gip:mt "cell_name" (- fx 14960.5) y (strcat "  " (gip:g r "name")) nil)
       (if (/= (gip:gn r "type" "") "") (gip:mt (if (= (gip:g r "type") $S212) "cell_type7" "cell_type") (- fx 9760.5) y (gip:g r "type") nil))
       (if (/= (gip:gn r "maker" "") "") (gip:mt (if (= (gip:g r "maker") $S212) "cell_type7" "cell_maker") (- fx 5735.5) y (gip:g r "maker") nil))
       (if (/= (gip:gn r "unit" "") "") (gip:mt "cell_unit" (- fx 4210.5) y (gip:g r "unit") nil))
       (if (gip:g r "qty") (gip:mt "cell_qty" (- fx 3060.5) y (if (= (type (gip:g r "qty")) 'STR) (gip:g r "qty") (itoa (gip:g r "qty"))) nil))))
    (setq ri (1+ ri))))
;;; ============================================================================
;;; Альбом: поиск листов шаблона, построение, нумерация, ведомость, хранение состояния,
;;; обновление по монтажной схеме
;;; ============================================================================
(setq *gip:SW* 20960.5 *gip:SHH* 14850.0)
(setq *gip:dO* '(-19960.1234209281 10782.4628509109))  ; начало шапки схемы относительно точки рамки F

(defun gip:F->O (F) (list (+ (car F) (car *gip:dO*)) (+ (cadr F) (cadr *gip:dO*))))

;; листы шаблона: рамки А3-GIP-ALBOM без метки GIPGEN и их названия из штампа
(defun gip:template-sheets (/ ss i e o ip nm res ttl tss j te tp)
  (setq res nil)
  (if (setq ss (ssget "_X" '((0 . "INSERT"))))
    (progn
      (setq i 0)
      (while (< i (sslength ss))
        (setq e (ssname ss i) i (1+ i))
        (setq o (vlax-ename->vla-object e))
        (setq nm (vl-catch-all-apply 'vlax-get (list o 'EffectiveName)))
        (if (and (= nm $S106) (not (assoc -3 (entget e (list *gip:app*)))))
          (setq res (cons (list (cdr (assoc 10 (entget e))) e) res))))))
  ;; названия
  (setq tss (ssget "_X" '((0 . "MTEXT"))))
  (mapcar '(lambda (fr / F ttl no tot j te tp)
             (setq F (car fr) ttl "" no nil tot nil j 0)
             (if tss
               (while (< j (sslength tss))
                 (setq te (ssname tss j) j (1+ j))
                 (if (not (assoc -3 (entget te (list *gip:app*))))
                   (progn
                     (setq tp (cdr (assoc 10 (entget te))))
                     (cond ((and (equal (- (car tp) (car F)) -6250.0 3.0) (equal (- (cadr tp) (cadr F)) 625.0 3.0)) (setq ttl (gip:mt-plain (entget te))))
                           ((and (equal (- (car tp) (car F)) -2000.0 3.0) (equal (- (cadr tp) (cadr F)) 1250.0 3.0)) (setq no te))
                           ((and (equal (- (car tp) (car F)) -1150.0 3.0) (equal (- (cadr tp) (cadr F)) 1250.0 3.0)) (setq tot te)))))))
             (list (cons "F" F) (cons "title" ttl) (cons "no" no) (cons "tot" tot) (cons "role" (gip:sheet-role ttl))))
          res))

(defun gip:mt-plain (ed / s)
  (setq s "")
  (foreach p ed (if (= (car p) 3) (setq s (strcat s (cdr p)))))
  (setq s (strcat s (cdr (assoc 1 ed))))
  (gip:mt-strip s))
(defun gip:mt-strip (s / r i c n)
  ;; убрать коды форматирования MTEXT
  (setq r "" i 1 n (strlen s))
  (while (<= i n)
    (setq c (substr s i 1))
    (cond ((and (= c "\\") (< i n) (member (substr s (1+ i) 1) '("P")))
           (setq r (strcat r " ") i (+ i 2)))
          ((and (= c "\\") (< i n) (member (strcase (substr s (1+ i) 1)) '("A" "C" "F" "H" "Q" "T" "W" "P")))
           (while (and (<= i n) (/= (substr s i 1) ";")) (setq i (1+ i))) (setq i (1+ i)))
          ((and (= c "\\") (< i n) (member (strcase (substr s (1+ i) 1)) '("L" "O" "K")))
           (setq i (+ i 2)))
          ((member c '("{" "}")) (setq i (1+ i)))
          (T (setq r (strcat r c) i (1+ i)))))
  (gip:trim r))

(defun gip:sheet-role (ttl / t1)
  (setq t1 (gip:lower ttl))
  (cond ((gip:has t1 $S237) "od")
        ((gip:has t1 $S238) "ol")
        ((gip:has t1 $S239) "frag")
        ((gip:has t1 $S240) "cable")
        ((gip:has t1 $S241) "legend")
        ((gip:has t1 $S242) "plan_p")
        ((gip:has t1 $S243) "plan_l")
        ((gip:has t1 $S244) "plan_d")
        ((gip:has t1 $S245) "mont")
        ((gip:has t1 $S246) "spec")
        (T "other")))

(defun gip:sheet-by-role (sheets role) (vl-some '(lambda (s) (if (= (gip:g s "role") role) s)) sheets))

;; удалить всё, что построено раньше
(defun gip:clear (/ ss i n)
  (setq n 0)
  (if (setq ss (ssget "_X" (list (list -3 (list *gip:app*)))))
    (progn (setq i 0) (while (< i (sslength ss)) (entdel (ssname ss i)) (setq i (1+ i) n (1+ n)))))
  n)

;; ---------------------------------------------------------------- состояние в чертеже
(defun gip:dict-get (key / d x s)
  (if (setq d (dictsearch (namedobjdict) key))
    (progn (setq s "") (foreach p d (if (= (car p) 1) (setq s (strcat s (cdr p))))) s)))
(defun gip:dict-put (key s / x l)
  (dictremove (namedobjdict) key)
  (setq l (list '(0 . "XRECORD") '(100 . "AcDbXrecord")))
  (while (> (strlen s) 200) (setq l (append l (list (cons 1 (substr s 1 200)))) s (substr s 201)))
  (setq l (append l (list (cons 1 s))))
  (setq x (entmakex l))
  (dictadd (namedobjdict) key x))
(defun gip:save-state (S) (gip:dict-put "GIPSHCHIT" (vl-prin1-to-string S)))
(defun gip:load-state (/ s) (if (setq s (gip:dict-get "GIPSHCHIT")) (read s)))
(defun gip:save-geo (g) (gip:dict-put "GIPSHCHIT_GEO" (vl-prin1-to-string g)))
(defun gip:load-geo (/ s) (if (setq s (gip:dict-get "GIPSHCHIT_GEO")) (read s)))

;; прокладка кабелей: вид блока «ЭОМ_Схема подвода кабеля_GIP» на листе схемы подвода
(defun gip:set-route (S / ss i o nm r)
  (setq r (gip:gn S "route" (car *gip:routes*)))
  (if (setq ss (ssget "_X" '((0 . "INSERT"))))
    (progn (setq i 0)
      (while (< i (sslength ss))
        (setq o (vlax-ename->vla-object (ssname ss i)) i (1+ i))
        (setq nm (vl-catch-all-apply 'vlax-get (list o 'EffectiveName)))
        (if (= nm $S247) (gip:set-dyn o $S105 r))))))

;; ---------------------------------------------------------------- построение альбома
(defun gip:build (S / BRD sheets od dsup F0 pages k n nOL Fm box secs spages p Fp total roles num tblist m ol-titles)
  (setq *gip:S* S *gip:b* (gip:brand (gip:g S "brand")) *gip:tag* "gip")
  (if (not (and (tblsearch "BLOCK" $S106) (tblsearch "BLOCK" $S248) (tblsearch "BLOCK" "GIPM_ab_a1")))
    (progn
      (alert $S249)
      (exit)))
  (regapp *gip:app*) (regapp *gip:dev-app*)
  (gip:clear)
  (setq BRD (gip:board S))
  (setq sheets (gip:template-sheets))
  (setq od (gip:sheet-by-role sheets "od") dsup (gip:sheet-by-role sheets "plan_d"))
  ;; опорные точки
  (setq F0 (if od (list (car (gip:g od "F")) (- (cadr (gip:g od "F")) *gip:SHH*)) (list 0.0 0.0)))
  (setq Fm (if dsup (list (+ (car (gip:g dsup "F")) *gip:SW*) (cadr (gip:g dsup "F"))) (list (+ (car F0) (* 4 *gip:SW*)) (cadr F0))))
  ;; однолинейная схема
  (setq pages (gip:ol-pages BRD (gip:g S "kup")) n (length pages) k 0 ol-titles nil)
  (foreach sc pages
    (setq *gip:tag* (strcat "ol" (itoa (1+ k))))
    (setq ol-titles (append ol-titles (list (gip:ol-sheet S BRD sc k n (+ (car F0) (car *gip:dO*) (* k *gip:SW*)) (+ (cadr F0) (cadr *gip:dO*))))))
    (setq k (1+ k)))
  (setq nOL n)
  ;; монтажная схема
  (setq *gip:tag* "mont")
  (gip:place "mont" (car Fm) (cadr Fm)
    $Q250)
  (gip:montage S BRD Fm)
  ;; спецификация
  (setq secs (gip:spec-sections S BRD sheets) spages (gip:spec-pages secs) p 0)
  (foreach rows spages
    (setq *gip:tag* (strcat "spec" (itoa (1+ p))))
    (setq Fp (cond (dsup (if (< p 2) (list (car (gip:g dsup "F")) (- (cadr (gip:g dsup "F")) (* (1+ p) *gip:SHH*)))
                             (list (+ (car (gip:g dsup "F")) (* (1- p) *gip:SW*)) (- (cadr (gip:g dsup "F")) (* 2 *gip:SHH*)))))
                   (T (list (+ (car F0) (* p *gip:SW*)) (- (cadr F0) (* 3 *gip:SHH*))))))
    (gip:spec-sheet rows Fp (itoa (1+ p)) (if (= p 0) (itoa (max 2 (length spages))) ""))
    (setq p (1+ p)))
  ;; нумерация листов шаблона и ведомость
  (gip:number-sheets sheets nOL ol-titles S)
  (gip:set-route S)
  (gip:save-state S)
  (gip:panel-save S BRD)
  (gip:save-geo (list (cons "mgeo" *gip:mgeo*) (cons "snap" (gip:montage-snapshot))))
  (setq *gip:board* BRD)
  BRD)

;; номера статических листов: ОД — 1, однолинейная 2..n+1, далее фрагмент, схема подвода, условные, планы, монтажная
(defun gip:number-sheets (sheets nOL ol-titles S / order no total list1 e k sh)
  (setq order '("frag" "cable" "legend" "plan_p" "plan_l" "plan_d") no (+ 2 nOL) list1 nil)
  (setq list1 (list (list "1" $S251)))
  (setq k 0)
  (foreach t1 ol-titles (setq list1 (append list1 (list (list (itoa (+ 2 k)) t1))) k (1+ k)))
  (foreach r order
    (if (setq sh (gip:sheet-by-role sheets r))
      (progn
        (if (setq e (gip:g sh "no")) (gip:set-mtext e (itoa no)))
        (setq list1 (append list1 (list (list (itoa no) (gip:g sh "title")))))
        (setq no (1+ no)))))
  (setq list1 (append list1 (list (list (itoa no) (strcat $S252 (gip:gn S "board" $S62))))))
  (setq total no)
  (if (and (setq sh (gip:sheet-by-role sheets "od")) (setq e (gip:g sh "tot"))) (gip:set-mtext e (itoa total)))
  (if (and sh (setq e (gip:g sh "no"))) (gip:set-mtext e "1"))
  (gip:fill-vedomost list1)
  list1)

(defun gip:set-mtext (e txt / ed full)
  (setq ed (entget e))
  (setq full "")
  (foreach p ed (if (= (car p) 3) (setq full (strcat full (cdr p)))))
  (setq full (strcat full (cdr (assoc 1 ed))))
  (setq ed (vl-remove-if '(lambda (p) (= (car p) 3)) ed))
  (entmod (subst (cons 1 (gip:mt-wrap full txt)) (assoc 1 ed) ed)))

;; ведомость рабочих чертежей (таблица AutoCAD на листе ОД)
(defun gip:fill-vedomost (rows / ss i e o tb nrow need r h)
  (setq tb nil)
  (if (setq ss (ssget "_X" '((0 . "ACAD_TABLE"))))
    (progn (setq i 0)
      (while (< i (sslength ss))
        (setq e (ssname ss i) i (1+ i) o (vlax-ename->vla-object e))
        (if (and (null tb) (= (gip:mt-strip (vlax-invoke o 'GetText 0 0)) $S253)) (setq tb o)))))
  (if tb
    (progn
      (setq nrow (vlax-get tb 'Rows) need (1+ (length rows)))
      (setq h (vl-catch-all-apply 'vlax-invoke (list tb 'GetRowHeight 1)))
      (if (vl-catch-all-error-p h) (setq h 800.0))
      (if (< nrow need) (vlax-invoke tb 'InsertRows (1- nrow) h (- need nrow)))
      (if (> nrow need) (vlax-invoke tb 'DeleteRows need (- nrow need)))
      (setq r 1)
      (foreach rw rows
        (vlax-invoke tb 'SetText r 0 (car rw))
        (vlax-invoke tb 'SetText r 1 (cadr rw))
        (setq r (1+ r))))))

;; ---------------------------------------------------------------- монтажная схема -> состояние
(defun gip:montage-devs (/ ss i e ed id ip o atts in res)
  (setq res nil)
  (if (setq ss (ssget "_X" (list '(0 . "INSERT") (list -3 (list *gip:dev-app*)))))
    (progn (setq i 0)
      (while (< i (sslength ss))
        (setq e (ssname ss i) i (1+ i) ed (entget e (list *gip:dev-app*)))
        (setq id (cdr (assoc 1000 (cdr (assoc *gip:dev-app* (cdr (assoc -3 ed)))))))
        (setq ip (cdr (assoc 10 ed)))
        (setq in nil o (vlax-ename->vla-object e))
        (foreach a (vlax-invoke o 'GetAttributes)
          (if (= (vlax-get a 'TagString) $S254) (setq in (vlax-get a 'TextString))))
        (setq res (cons (list id (car ip) (cadr ip) in) res)))))
  res)
(defun gip:montage-snapshot () (gip:montage-devs))

;; число из надписи номинала: "C16", " C16 230/400В ~", "NXB-63  C16", "40A"
(defun gip:parse-in (s / i n c r cand)
  (if s
    (progn
      (setq n (strlen s) i 1 cand nil)
      (while (and (<= i n) (null cand))
        (setq c (substr s i 1))
        (if (and (member c $Q255) (< i n) (wcmatch (substr s (1+ i) 1) "#"))
          (progn (setq r "" i (1+ i))
                 (while (and (<= i n) (wcmatch (substr s i 1) "#")) (setq r (strcat r (substr s i 1)) i (1+ i)))
                 (setq cand (atoi r)))
          (setq i (1+ i))))
      (if (null cand)
        (progn (setq i 1)
          (while (and (<= i n) (null cand))
            (if (wcmatch (substr s i 1) "#")
              (progn (setq r "")
                     (while (and (<= i n) (wcmatch (substr s i 1) "#")) (setq r (strcat r (substr s i 1)) i (1+ i)))
                     (if (and (<= i n) (member (substr s i 1) $Q256)) (setq cand (atoi r))))
              (setq i (1+ i))))))
      cand)))

;; пересчитать порядок аппаратов по их положению на монтажной схеме
(defun gip:sync-from-montage (S / geo mg mo x0 railC devs items R rails sorted order breaks prev ri bydev removed edit d dv id In l lid old)
  (setq geo (gip:load-geo) mg (gip:g geo "mgeo"))
  (if (and mg (setq devs (gip:montage-devs)))
    (progn
      (setq mo (gip:g mg "mo") railC (gip:g mg "railC") x0 (gip:g mg "x0") R (length railC))
      ;; в координаты pt
      (setq items (mapcar '(lambda (dv / x y best bi k)
                             (setq x (/ (- (cadr dv) (car mo)) (caddr mo)) y (/ (- (cadr mo) (caddr dv)) (caddr mo)))
                             (setq best nil bi 0 k 0)
                             (foreach c railC
                               (if (or (null best) (< (abs (- (+ y 112.0) c)) best)) (setq best (abs (- (+ y 112.0) c)) bi k))
                               (setq k (1+ k)))
                             ;; ниже последней рейки — новая рейка
                             (if (and railC (> (+ y 112.0) (+ (last railC) 260.0))) (setq bi (+ (1- R) (fix (/ (- (+ y 112.0) (last railC)) 330.0)))))
                             (list (car dv) bi x (nth 3 dv))) devs))
      (setq sorted (gip:msort items '(lambda (a b) (if (/= (cadr a) (cadr b)) (< (cadr a) (cadr b)) (< (caddr a) (caddr b))))))
      (setq order (mapcar 'car sorted) breaks nil prev -1)
      (foreach it sorted (if (and (/= (cadr it) prev) (>= prev 0)) (setq breaks (cons (car it) breaks))) (setq prev (cadr it)))
      (setq S (gip:s S "order" order) S (gip:s S "breaks" (reverse breaks)))
      (setq S (gip:s S "railsMin" (max (gip:gn S "railsMin" 0) (1+ (apply 'max (mapcar 'cadr sorted))))))
      (if (= (gip:g S "v") 2)
        (progn
          ;; режим таблицы: разрывы реек — по позиции, порядок и состав строк — по монтажной схеме
          (setq prev -1 ri 0 breaks nil)
          (foreach it sorted (if (and (/= (cadr it) prev) (>= prev 0)) (setq breaks (cons ri breaks))) (setq prev (cadr it) ri (1+ ri)))
          (setq S (gip:s S "breaks" nil) S (gip:s S "breakAt" (reverse breaks)))
          (setq S (gip:s S "rows" (gip:rows-from-montage S sorted)))
          (setq devs nil)))
      ;; удалённые с монтажной схемы групповые аппараты -> убрать линии; изменённые номиналы -> правки
      (setq removed (gip:g S "removed") edit (gip:g S "edit"))
      (foreach d (if devs (gip:g (gip:board S) "all"))
        (setq id (gip:g d "id"))
        (if (gip:starts id "L:")
          (progn
            (setq lid (substr id 3) dv (assoc id items))
            (if (null dv)
              (if (not (member lid removed)) (setq removed (append removed (list lid))))
              (if (and (setq In (gip:parse-in (nth 3 dv))) (/= In (gip:g d "In")))
                (setq old (gip:g edit lid) edit (gip:s edit lid (gip:s old "In" In))))))))
      (setq S (gip:s S "removed" removed) S (gip:s S "edit" edit))))
  S)

(defun gip:montage-changed (/ geo snap now)
  (setq geo (gip:load-geo) snap (gip:g geo "snap") now (gip:montage-devs))
  (not (equal (gip:msort snap '(lambda (a b) (< (car a) (car b)))) (gip:msort now '(lambda (a b) (< (car a) (car b)))) 0.5)))
;;; ============================================================================
;;; План из PDF дизайнера: подложка (квартира + мебель) одним блоком на листах планов
;;; и блоки ГИП (розетки, выключатели, светильники) на местах значков дизайнера.
;;; Данные готовит панель «План из PDF» (файл TEMPPREFIX\gip_plan_in.txt, по строке на объект):
;;;   (GIPPLAN 1 масштаб ширина высота "имя")
;;;   (L k x y x y ...) — полилиния, (C k ...) — замкнутая, (F k ...) — заливка; k: 0 квартира, 1 мебель
;;;   (S "p"|"l" "R"|"V"|"C" вид x y поворот°) — блок ГИП на силовом плане (p) или плане освещения (l)
;;; Координаты — мм от левого нижнего угла подложки. Всё созданное помечено xdata GIPPLAN
;;; (альбом при перестройке это не трогает; повторный импорт заменяет прежний).
;;; ============================================================================
(setq *gip:plan-app* "GIPPLAN" *gip:plan-file* "gip_plan_in.txt")
(setq *gip:plan-blocks* $Q257)
(setq *gip:plan-vis* (list
  (cons "R" (list $S258 $S259 $S260 $S261
                  $S262 $S263 $S264
                  $S265))
  (cons "V" (list $S266 $S267 $S268 $S269
                  $S270 $S271 $S272))
  (cons "C" (list $S273 $S274 $S275 $S276 $S277
                  $S278 $S279 $S280 $S281 $S282
                  $S283 $S284))))
;; центр плана на листе относительно точки рамки (как в проектах ГИП: над штампом, левее)
(setq *gip:plan-at* '(-9140.0 8390.0))

(defun gip:plan-tag () (list (list -3 (list *gip:plan-app* (cons 1000 "plan")))))

;; удалить прежний импорт
(defun gip:plan-clear (/ ss i n)
  (setq n 0)
  (if (setq ss (ssget "_X" (list (list -3 (list *gip:plan-app*)))))
    (progn (setq i 0) (while (< i (sslength ss)) (entdel (ssname ss i)) (setq i (1+ i) n (1+ n)))))
  n)

;; свободное имя блока подложки
(defun gip:plan-blkname (/ i nm)
  (setq i 1)
  (while (tblsearch "BLOCK" (setq nm (strcat "GIP_PLAN_" (itoa i)))) (setq i (1+ i)))
  nm)

;; список чисел -> точки 10
(defun gip:plan-pts (nums / r)
  (setq r nil)
  (while (cdr nums) (setq r (cons (list 10 (float (car nums)) (float (cadr nums))) r) nums (cddr nums)))
  (reverse r))

(defun gip:plan-ent (it / k pts col)
  (setq k (cadr it) pts (gip:plan-pts (cddr it)) col (if (= k 1) 8 7))
  (cond
    ((< (length pts) 2) nil)
    ((eq (car it) 'F)
     (entmake (append (list '(0 . "HATCH") '(100 . "AcDbEntity") '(8 . "0") (cons 62 col) '(100 . "AcDbHatch") '(10 0.0 0.0 0.0) '(210 0.0 0.0 1.0)
                            '(2 . "SOLID") '(70 . 1) '(71 . 0) '(91 . 1) '(92 . 7) '(72 . 1) '(73 . 1) (cons 93 (length pts)))
                      (apply 'append (mapcar '(lambda (p) (list (list 10 (cadr p) (caddr p) 0.0) '(42 . 0.0))) pts))
                      (list '(97 . 0) '(75 . 0) '(76 . 1) '(47 . 1.0) '(98 . 1) (list 10 (cadr (car pts)) (caddr (car pts)) 0.0)
                            '(450 . 0) '(451 . 0) '(460 . 0.0) '(461 . 0.0) '(452 . 0) '(462 . 0.0) '(453 . 0) '(470 . "")))))
    (T
     (entmake (append (list '(0 . "LWPOLYLINE") '(100 . "AcDbEntity") '(8 . "0") (cons 62 col) '(100 . "AcDbPolyline")
                            (cons 90 (length pts)) (cons 70 (if (eq (car it) 'C) 1 0)))
                      pts)))))

;; листы планов шаблона ГИП: силовой (p), освещения (l), ДСУП (d)
(defun gip:plan-sheets (/ sh r)
  (setq r nil)
  (foreach sh (gip:template-sheets)
    (cond ((= (gip:g sh "role") "plan_p") (setq r (cons (cons "p" (gip:g sh "F")) r)))
          ((= (gip:g sh "role") "plan_l") (setq r (cons (cons "l" (gip:g sh "F")) r)))
          ((= (gip:g sh "role") "plan_d") (setq r (cons (cons "d" (gip:g sh "F")) r)))))
  r)

;; вставка с меткой GIPPLAN
(defun gip:plan-insert (name x y rot lay / obj e)
  (setq obj (vla-insertblock (gip:ms) (vlax-3d-point x y 0.0) name 1.0 1.0 1.0 (* rot (/ pi 180.0))))
  (vla-put-layer obj (gip:layer lay))
  (setq e (vlax-vla-object->ename obj))
  (entmod (append (entget e) (gip:plan-tag)))
  obj)

(defun gip:plan-import (fn / f l it head blk W H nU syms sheets org pt sh obj bl n0 nS sd)
  (if (not (and fn (findfile fn) (setq f (open fn "r"))))
    (progn (princ $S285) nil)
    (progn
      (regapp *gip:plan-app*)
      (setq head (read (read-line f)))
      (if (not (and (listp head) (eq (car head) 'GIPPLAN)))
        (progn (close f) (princ $S286) nil)
        (progn
          (setq W (nth 3 head) H (nth 4 head) nU 0 syms nil)
          (princ $S287)
          (setq blk (gip:plan-blkname))
          (entmake (list '(0 . "BLOCK") (cons 2 blk) '(70 . 0) '(10 0.0 0.0 0.0)))
          (while (setq l (read-line f))
            (if (/= l "")
              (progn
                (setq it (read l))
                (cond ((member (car it) '(L C F)) (if (gip:plan-ent it) (setq nU (1+ nU))))
                      ((eq (car it) 'S) (setq syms (cons it syms)))))))
          (close f)
          (entmake '((0 . "ENDBLK")))
          (setq n0 (gip:plan-clear))
          (setq sheets (gip:plan-sheets) nS 0)
          (if (null sheets)
            ;; не шаблон ГИП: одна точка вставки, силовой план и план освещения рядом
            (if (setq pt (getpoint $S288))
              (setq sheets (list (cons "p" (list (+ (car pt) (- (car *gip:plan-at*)) (/ W 2.0)) (- (cadr pt) (cadr *gip:plan-at*) (- (/ H 2.0)))))
                                 (cons "l" (list (+ (car pt) (- (car *gip:plan-at*)) (/ W 2.0) W 2000.0) (- (cadr pt) (cadr *gip:plan-at*) (- (/ H 2.0)))))))))
          (foreach sh sheets
            ;; левый нижний угол подложки: центр плана в точке *gip:plan-at* от рамки
            (setq org (list (- (+ (car (cdr sh)) (car *gip:plan-at*)) (/ W 2.0)) (- (+ (cadr (cdr sh)) (cadr *gip:plan-at*)) (/ H 2.0))))
            (gip:plan-insert blk (car org) (cadr org) 0.0 $S289)
            (foreach s syms
              (if (= (nth 1 s) (car sh))
                (progn
                  (setq bl (assoc (nth 2 s) *gip:plan-blocks*))
                  (if (and bl (tblsearch "BLOCK" (cadr bl)))
                    (progn
                      (setq obj (gip:plan-insert (cadr bl) (+ (car org) (nth 4 s)) (+ (cadr org) (nth 5 s)) (nth 6 s) (caddr bl)))
                      (if (setq sd (nth (nth 3 s) (cdr (assoc (nth 2 s) *gip:plan-vis*)))) (gip:set-vis obj (cadr bl) sd))
                      (setq nS (1+ nS))))))))
          (princ (strcat $S290 blk $S291 (itoa nU) $S292 (itoa (length sheets)) $S293 (itoa nS)
                         (if (> n0 0) (strcat $S294) "") "."))
          blk)))))

;; из панели: файл во временной папке
(defun c:GIPPLANIMPORT () (gip:plan-import (strcat (getvar "TEMPPREFIX") *gip:plan-file*)) (princ))
;; вручную: выбрать файл, сохранённый панелью
(defun c:GIPPLAN (/ fn)
  (if (setq fn (getfiled $S295 (getvar "TEMPPREFIX") "txt" 0)) (gip:plan-import fn))
  (princ))
;;; ============================================================================
;;; Команды, окно параметров, импорт ссылки с сайта, автообновление
;;; ============================================================================

;; ---------------------------------------------------------------- base64url + UTF-8 + JSON (ссылка конструктора)
(defun gip:b64val (c)
  (cond ((and (>= c 65) (<= c 90)) (- c 65)) ((and (>= c 97) (<= c 122)) (- c 71)) ((and (>= c 48) (<= c 57)) (+ c 4))
        ((member c '(43 45)) 62) ((member c '(47 95)) 63) (T nil)))
(defun gip:b64 (s / vals out i a b c d)
  (setq vals (vl-remove 'nil (mapcar 'gip:b64val (vl-string->list s))) out nil i 0)
  (while (< i (length vals))
    (setq a (nth i vals) b (nth (+ i 1) vals) c (nth (+ i 2) vals) d (nth (+ i 3) vals))
    (if b (setq out (cons (logand 255 (+ (lsh a 2) (lsh b -4))) out)))
    (if c (setq out (cons (logand 255 (+ (lsh b 4) (lsh c -2))) out)))
    (if d (setq out (cons (logand 255 (+ (lsh c 6) d)) out)))
    (setq i (+ i 4)))
  (reverse out))
(defun gip:utf8 (bytes / r b c)
  (setq r nil)
  (while bytes
    (setq b (car bytes) bytes (cdr bytes))
    (cond ((< b 128) (setq c b))
          ((< b 224) (setq c (+ (lsh (logand b 31) 6) (logand (car bytes) 63)) bytes (cdr bytes)))
          ((< b 240) (setq c (+ (lsh (logand b 15) 12) (lsh (logand (car bytes) 63) 6) (logand (cadr bytes) 63)) bytes (cddr bytes)))
          (T (setq c 63 bytes (cdddr bytes))))
    (setq r (cons c r)))
  (apply 'strcat (mapcar 'chr (reverse r))))

;; JSON: объект -> список пар (ключ . значение), массив -> список, true -> T, false/null -> nil
(defun gip:json (s / *p* *s*)
  (setq *s* s *p* 1)
  (gip:j-val))
(defun gip:j-ch () (substr *s* *p* 1))
(defun gip:j-ws () (while (member (gip:j-ch) '(" " "\t" "\n" "\r")) (setq *p* (1+ *p*))))
(defun gip:j-val (/ c)
  (gip:j-ws) (setq c (gip:j-ch))
  (cond ((= c "{") (gip:j-obj)) ((= c "[") (gip:j-arr)) ((= c "\"") (gip:j-str))
        ((= (substr *s* *p* 4) "true") (setq *p* (+ *p* 4)) T)
        ((= (substr *s* *p* 5) "false") (setq *p* (+ *p* 5)) nil)
        ((= (substr *s* *p* 4) "null") (setq *p* (+ *p* 4)) nil)
        (T (gip:j-num))))
(defun gip:j-obj (/ r k v)
  (setq *p* (1+ *p*) r nil) (gip:j-ws)
  (if (= (gip:j-ch) "}") (setq *p* (1+ *p*))
    (progn
      (while (progn (gip:j-ws) (setq k (gip:j-str)) (gip:j-ws) (setq *p* (1+ *p*)) (setq v (gip:j-val)) (setq r (cons (cons k v) r))
                    (gip:j-ws) (= (gip:j-ch) ","))
        (setq *p* (1+ *p*)))
      (setq *p* (1+ *p*))))
  (reverse r))
(defun gip:j-arr (/ r)
  (setq *p* (1+ *p*) r nil) (gip:j-ws)
  (if (= (gip:j-ch) "]") (setq *p* (1+ *p*))
    (progn
      (while (progn (setq r (cons (gip:j-val) r)) (gip:j-ws) (= (gip:j-ch) ","))
        (setq *p* (1+ *p*)))
      (setq *p* (1+ *p*))))
  (reverse r))
(defun gip:j-str (/ r c e)
  (setq *p* (1+ *p*) r "")
  (while (/= (setq c (gip:j-ch)) "\"")
    (if (= c "\\")
      (progn (setq e (substr *s* (1+ *p*) 1))
             (cond ((= e "u") (setq r (strcat r (chr (gip:hex (substr *s* (+ *p* 2) 4)))) *p* (+ *p* 6)))
                   ((= e "n") (setq r (strcat r "\n") *p* (+ *p* 2)))
                   ((= e "t") (setq r (strcat r "\t") *p* (+ *p* 2)))
                   (T (setq r (strcat r e) *p* (+ *p* 2)))))
      (setq r (strcat r c) *p* (1+ *p*))))
  (setq *p* (1+ *p*))
  r)
(defun gip:j-num (/ st n)
  (setq st *p*)
  (while (member (gip:j-ch) (quote ("-" "+" "." "0" "1" "2" "3" "4" "5" "6" "7" "8" "9" "e" "E"))) (setq *p* (1+ *p*)))
  (setq n (substr *s* st (- *p* st)))
  (if (or (vl-string-search "." n) (vl-string-search "e" n) (vl-string-search "E" n)) (atof n) (atoi n)))

;; ссылка конструктора -> состояние GIP-ЩИТ
(defun gip:state-from-link (txt / p h j S0 S k v ks)
  (setq p (vl-string-search "shchit=" txt))
  (if p
    (progn
      (setq h (substr txt (+ p 8)))
      (if (setq p (vl-string-search "&" h)) (setq h (substr h 1 p)))
      (setq j (gip:json (gip:utf8 (gip:b64 h))))
      (setq S (gip:default-state (gip:gn j "tpl" "k1")))
      (foreach k '("tpl" "phases" "inA" "inPoles" "brand" "prot" "railW" "railsMin" "kc" "floor" "ac" "heater" "light" "sockets" "order")
        (if (assoc k j) (setq S (gip:s S k (cdr (assoc k j))))))
      (foreach k '("relay" "km" "fire") (setq S (gip:s S k (if (cdr (assoc k j)) T nil))))
      (setq S (gip:s S "app" (mapcar '(lambda (x) (cons (car x) (if (cdr x) T nil))) (gip:g j "app"))))
      (setq S (gip:s S "removed" (mapcar 'car (vl-remove-if-not 'cdr (gip:g j "removed")))))
      (setq S (gip:s S "breaks" (mapcar 'car (vl-remove-if-not 'cdr (gip:g j "breaks")))))
      (setq S (gip:s S "edit" (gip:g j "edit")))
      (setq S (gip:s S "custom" (gip:g j "custom")))
      (if (= (type (gip:g S "kc")) 'INT) (setq S (gip:s S "kc" (float (gip:g S "kc")))))
      (setq S (gip:s S "area" (gip:g (gip:tpl (gip:g S "tpl")) "area")))
      S)))

;; текст из буфера обмена Windows (ссылка, скопированная кнопкой на сайте)
(defun gip:clipboard (/ html win cb txt)
  (setq txt (vl-catch-all-apply
              '(lambda ()
                 (setq html (vlax-create-object "htmlfile"))
                 (setq win (vlax-get html 'ParentWindow) cb (vlax-get win 'ClipBoardData))
                 (vlax-invoke cb 'GetData "Text"))))
  (if html (vl-catch-all-apply 'vlax-release-object (list html)))
  (if (= (type txt) 'STR) txt))
(defun gip:ask-link (/ txt)
  (setq txt (gip:clipboard))
  (if (and txt (vl-string-search "shchit=" txt))
    (progn (princ $S296) txt)
    (getstring T $S297)))

;; ---------------------------------------------------------------- построение с сообщениями
(defun gip:run (S / doc r t0)
  (setq doc (vla-get-activedocument (vlax-get-acad-object)) *gip:busy* T)
  (if (not *gip:in-reactor*) (vla-startundomark doc))
  (setq r (vl-catch-all-apply 'gip:build (list S)))
  (if (not *gip:in-reactor*) (vla-endundomark doc))
  (setq *gip:busy* nil)
  (if (vl-catch-all-error-p r)
    (progn (princ (strcat $S298 (vl-catch-all-error-message r))) nil)
    (progn
      (princ (strcat $S299 (itoa (length (gip:g r "lines")))
                     $S300 (itoa (length (gip:g r "all"))) $S301 (itoa (length (gip:g r "rails")))
                     $S302 (itoa (gip:g r "cap")) $S189))
      r)))

;; ---------------------------------------------------------------- окно параметров (DCL; надписи задаются из программы)
(setq *gip:dcl*
'("gip_main : dialog { label = \"GIP\"; key = \"dlg\";"
  " : row {"
  "  : boxed_column { key = \"c1\"; label = \"\"; width = 34;"
  "   : text { key = \"l_tpl\"; } : popup_list { key = \"tpl\"; }"
  "   : text { key = \"l_area\"; } : edit_box { key = \"area\"; edit_width = 8; }"
  "   : text { key = \"l_ph\"; } : popup_list { key = \"phases\"; }"
  "   : text { key = \"l_inA\"; } : popup_list { key = \"inA\"; }"
  "   : text { key = \"l_inP\"; } : popup_list { key = \"inPoles\"; }"
  "   : text { key = \"l_brand\"; } : popup_list { key = \"brand\"; }"
  "   : text { key = \"l_prot\"; } : popup_list { key = \"prot\"; }"
  "   : text { key = \"l_rail\"; } : popup_list { key = \"railW\"; }"
  "   : text { key = \"l_kc\"; } : edit_box { key = \"kc\"; edit_width = 8; }"
  "  }"
  "  : boxed_column { key = \"c2\"; label = \"\"; width = 34;"
  "   : text { key = \"l_relay\"; } : popup_list { key = \"relay\"; }"
  "   : text { key = \"l_km\"; } : popup_list { key = \"km\"; }"
  "   : text { key = \"l_fire\"; } : popup_list { key = \"fire\"; }"
  "   : text { key = \"l_fl\"; } : popup_list { key = \"floorShield\"; }"
  "   : text { key = \"l_kup\"; } : popup_list { key = \"kup\"; }"
  "   : text { key = \"l_floor\"; } : popup_list { key = \"floor\"; }"
  "   : text { key = \"l_ac\"; } : popup_list { key = \"ac\"; }"
  "   : text { key = \"l_heater\"; } : popup_list { key = \"heater\"; }"
  "  }"
  "  : boxed_column { key = \"c3\"; label = \"\"; width = 34;"
  "   : text { key = \"l_hob\"; } : popup_list { key = \"hob\"; }"
  "   : text { key = \"l_oven\"; } : popup_list { key = \"oven\"; }"
  "   : text { key = \"l_fridge\"; } : popup_list { key = \"fridge\"; }"
  "   : text { key = \"l_dw\"; } : popup_list { key = \"dw\"; }"
  "   : text { key = \"l_wash\"; } : popup_list { key = \"wash\"; }"
  "   : text { key = \"l_dry\"; } : popup_list { key = \"dry\"; }"
  "   : text { key = \"l_leak\"; } : popup_list { key = \"leak\"; }"
  "  }"
  " }"
  " : boxed_column { key = \"c4\"; label = \"\";"
  "  : text { key = \"l_light\"; } : edit_box { key = \"light\"; edit_width = 100; edit_limit = 256; }"
  "  : text { key = \"l_sock\"; } : edit_box { key = \"sockets\"; edit_width = 100; edit_limit = 256; }"
  "  : row { : text { key = \"l_board\"; } : edit_box { key = \"board\"; edit_width = 10; } : text { key = \"l_stage\"; } : popup_list { key = \"stage\"; width = 18; } }"
  " }"
  " : row { : button { key = \"b_link\"; label = \"Link...\"; } : button { key = \"b_groups\"; label = \"Groups...\"; } : spacer { width = 10; } ok_cancel; }"
  " : text { key = \"msg\"; }"
  "}"
  "gip_groups : dialog { label = \"GIP\";"
  " : list_box { key = \"lst\"; width = 110; height = 22; tabs = \"6 46 56 70 82 92\"; }"
  " : row {"
  "  : column { : text { key = \"l_gname\"; } : edit_box { key = \"gname\"; edit_width = 40; } }"
  "  : column { : text { key = \"l_gin\"; } : popup_list { key = \"gin\"; width = 10; } }"
  "  : column { : text { key = \"l_gcab\"; } : edit_box { key = \"gcab\"; edit_width = 10; } }"
  "  : column { : text { key = \"l_gp\"; } : edit_box { key = \"gp\"; edit_width = 8; } }"
  "  : column { : text { key = \"l_gph\"; } : popup_list { key = \"gph\"; width = 10; } }"
  " }"
  " : row { : button { key = \"b_apply\"; label = \"Apply\"; } : button { key = \"b_del\"; label = \"Delete\"; } : button { key = \"b_add\"; label = \"Add\"; } : button { key = \"b_restore\"; label = \"Restore\"; } : spacer { width = 10; } ok_button; }"
  "}"))

(defun gip:dcl-file (/ f fn)
  (setq fn (vl-filename-mktemp "gipsh" nil ".dcl"))
  (setq f (open fn "w"))
  (foreach l *gip:dcl* (write-line l f))
  (close f)
  fn)

(setq *gip:yesno* $Q303)
(setq *gip:tpl-keys* '("studio" "k1" "k2" "k3"))
(setq *gip:brand-keys* '("abb" "iek" "dekraft" "chint"))
(setq *gip:inA-list* '(16 20 25 32 40 50 63))

(defun gip:fill (key items) (start_list key) (mapcar 'add_list items) (end_list))
(defun gip:yn (key v) (gip:fill key *gip:yesno*) (set_tile key (if v "0" "1")))
(defun gip:get-yn (key) (= (get_tile key) "0"))

(defun gip:dlg-init (S / app)
  (foreach p (list $Q304 $Q305 $Q306
                   $Q307 $Q308 $Q309
                   $Q310 $Q311 $Q312
                   $Q313 $Q314 $Q315
                   $Q316 $Q317 $Q318
                   $Q319 $Q320 $Q321 $Q322
                   $Q323 $Q324 $Q325 $Q326
                   $Q327
                   $Q328 $Q329
                   $Q330 $Q331
                   $Q332 $Q333)
    (set_tile (car p) (cdr p)))
  (gip:fill "tpl" (mapcar '(lambda (k) (gip:g (gip:tpl k) "name")) *gip:tpl-keys*))
  (gip:fill "phases" $Q334)
  (gip:fill "inA" (mapcar 'itoa *gip:inA-list*))
  (gip:fill "inPoles" '("3P" "4P"))
  (gip:fill "brand" '("ABB" "IEK" "Dekraft" "CHINT"))
  (gip:fill "prot" $Q335)
  (gip:fill "railW" '("12" "18" "24"))
  (gip:fill "floor" '("0" "1" "2" "3" "4"))
  (gip:fill "ac" '("0" "1" "2" "3" "4"))
  (gip:fill "heater" $Q336)
  (gip:fill "stage" $Q337)
  (gip:dlg-set S))

(defun gip:dlg-set (S / app)
  (set_tile "tpl" (itoa (gip:nz (gip:index (gip:g S "tpl") *gip:tpl-keys*) 0)))
  (set_tile "area" (gip:fmtz (gip:gn S "area" 50.0) 1))
  (set_tile "phases" (if (= (gip:g S "phases") 3) "1" "0"))
  (set_tile "inA" (itoa (gip:nz (gip:index (gip:g S "inA") *gip:inA-list*) 3)))
  (set_tile "inPoles" (if (= (gip:g S "inPoles") 4) "1" "0"))
  (set_tile "brand" (itoa (gip:nz (gip:index (gip:g S "brand") *gip:brand-keys*) 0)))
  (set_tile "prot" (if (= (gip:g S "prot") "rcd") "1" "0"))
  (set_tile "railW" (itoa (gip:nz (gip:index (gip:g S "railW") '(12 18 24)) 1)))
  (set_tile "kc" (gip:fmtz (gip:gn S "kc" 0.4) 2))
  (gip:yn "relay" (gip:g S "relay")) (gip:yn "km" (gip:g S "km")) (gip:yn "fire" (gip:g S "fire"))
  (gip:yn "floorShield" (gip:g S "floorShield")) (gip:yn "kup" (gip:g S "kup"))
  (set_tile "floor" (itoa (min 4 (gip:gn S "floor" 0)))) (set_tile "ac" (itoa (min 4 (gip:gn S "ac" 0))))
  (set_tile "heater" (cond ((= (gip:g S "heater") "boiler") "1") ((= (gip:g S "heater") "flow") "2") (T "0")))
  (setq app (gip:g S "app"))
  (foreach k '("hob" "oven" "fridge" "dw" "wash" "dry" "leak") (gip:yn k (gip:g app k)))
  (set_tile "light" (gip:join (gip:g S "light") ", "))
  (set_tile "sockets" (gip:join (gip:g S "sockets") ", "))
  (set_tile "board" (gip:gn S "board" $S62))
  (set_tile "stage" (if (= (gip:g S "stage") $S338) "1" "0")))

(defun gip:csv (s) (vl-remove "" (mapcar 'gip:trim (gip:split s ","))))

(defun gip:dlg-read (S / app v)
  (setq S (gip:s S "tpl" (nth (atoi (get_tile "tpl")) *gip:tpl-keys*)))
  (if (setq v (distof (gip:repl (get_tile "area") "," "."))) (setq S (gip:s S "area" (float v))))
  (setq S (gip:s S "phases" (if (= (get_tile "phases") "1") 3 1)))
  (setq S (gip:s S "inA" (nth (atoi (get_tile "inA")) *gip:inA-list*)))
  (setq S (gip:s S "inPoles" (if (= (get_tile "inPoles") "1") 4 3)))
  (setq S (gip:s S "brand" (nth (atoi (get_tile "brand")) *gip:brand-keys*)))
  (setq S (gip:s S "prot" (if (= (get_tile "prot") "1") "rcd" "dif")))
  (setq S (gip:s S "railW" (nth (atoi (get_tile "railW")) '(12 18 24))))
  (if (setq v (distof (gip:repl (get_tile "kc") "," "."))) (setq S (gip:s S "kc" (float v))))
  (foreach k '("relay" "km" "fire" "floorShield" "kup") (setq S (gip:s S k (gip:get-yn k))))
  (setq S (gip:s S "floor" (atoi (get_tile "floor"))) S (gip:s S "ac" (atoi (get_tile "ac"))))
  (setq S (gip:s S "heater" (nth (atoi (get_tile "heater")) '("none" "boiler" "flow"))))
  (setq app nil)
  (foreach k '("hob" "oven" "fridge" "dw" "wash" "dry" "leak") (setq app (append app (list (cons k (gip:get-yn k))))))
  (setq S (gip:s S "app" app))
  (setq S (gip:s S "light" (gip:csv (get_tile "light"))) S (gip:s S "sockets" (gip:csv (get_tile "sockets"))))
  (setq S (gip:s S "board" (gip:trim (get_tile "board"))))
  (setq S (gip:s S "stage" (if (= (get_tile "stage") "1") $S338 $S63)))
  S)

;; список групп для окна «Группы»
(defun gip:grp-items (S) (gip:build-lines S))
(defun gip:grp-text (l)
  (strcat (cond ((= (gip:g l "cat") "light") $S91) (T $S92)) "\t" (gip:g l "name") "\t" (itoa (gip:g l "In")) " A\t"
          (gip:repl (gip:g l "cable") $S94 "x") "\t" (gip:f1 (gip:g l "p")) $S339 (gip:gn l "phase" "")))

(defun gip:groups-dlg (dcl S / lines sel res e o id nm In cab p ph)
  (setq lines (gip:grp-items S) sel 0)
  (if (new_dialog "gip_groups" dcl)
    (progn
      (foreach p (list $Q340 $Q341 $Q342 $Q343
                       $Q344 $Q345 $Q346 $Q347
                       $Q348)
        (set_tile (car p) (cdr p)))
      (gip:fill "gin" (mapcar 'itoa *gip:std-in*))
      (gip:fill "gph" $Q349)
      (defun gip:g-refresh () (setq lines (gip:grp-items S)) (gip:fill "lst" (mapcar 'gip:grp-text lines)) (set_tile "lst" (itoa (min sel (max 0 (1- (length lines)))))) (gip:g-show))
      (defun gip:g-show (/ l)
        (if (setq l (nth sel lines))
          (progn (set_tile "gname" (gip:g l "name")) (set_tile "gin" (itoa (gip:nz (gip:index (gip:g l "In") *gip:std-in*) 3)))
                 (set_tile "gcab" (gip:repl (gip:g l "cable") $S94 "x")) (set_tile "gp" (gip:fmtz (gip:g l "p") 2))
                 (set_tile "gph" (itoa (gip:nz (gip:index (gip:g l "phase") '("auto" "L1" "L2" "L3")) 0))))))
      (defun gip:g-apply (/ l id o v cab)
        ;; в правки попадает только то, что изменено в окне
        (if (setq l (nth sel lines))
          (progn
            (setq id (gip:g l "id") o (gip:g (gip:g S "edit") id))
            (if (/= (get_tile "gname") (gip:g l "name")) (setq o (gip:s o "name" (get_tile "gname"))))
            (setq v (nth (atoi (get_tile "gin")) *gip:std-in*))
            (if (/= v (gip:g l "In")) (setq o (gip:s o "In" v)))
            (setq cab (gip:repl (gip:repl (get_tile "gcab") "x" $S94) $S214 $S94))
            (if (/= cab (gip:g l "cable")) (setq o (gip:s o "cable" cab)))
            (if (and (setq v (distof (gip:repl (get_tile "gp") "," "."))) (not (equal v (gip:g l "p") 1e-6))) (setq o (gip:s o "p" (float v))))
            (setq v (nth (atoi (get_tile "gph")) '("" "L1" "L2" "L3")))
            (if (and (/= v "") (/= v (gip:g l "phase"))) (setq o (gip:s o "phase" v)))
            (if o (setq S (gip:s S "edit" (gip:s (gip:g S "edit") id o))))
            (gip:g-refresh))))
      (gip:g-refresh)
      (action_tile "lst" "(setq sel (atoi $value)) (gip:g-show)")
      (action_tile "b_apply" "(gip:g-apply)")
      (action_tile "b_del" "(if (nth sel lines) (progn (setq S (gip:s S \"removed\" (append (gip:g S \"removed\") (list (gip:g (nth sel lines) \"id\"))))) (gip:g-refresh)))")
      (action_tile "b_add" (strcat "(setq S (gip:s S \"custom\" (append (gip:g S \"custom\") (list (list (cons \"id\" (strcat \"c\" (itoa (length (gip:g S \"custom\"))) \"_\" (rtos (getvar \"DATE\") 2 6))) (cons \"name\" \"" $S350 "\") (cons \"prot\" \"d\") (cons \"poles\" 1) (cons \"In\" 16) (cons \"p\" 1.0)))))) (setq sel 999) (gip:g-refresh)"))
      (action_tile "b_restore" "(setq S (gip:s S \"removed\" nil)) (gip:g-refresh)")
      (start_dialog)))
  S)

(defun gip:dialog (S / dcl id res S2)
  (setq dcl (load_dialog (gip:dcl-file)))
  (setq res 2)
  (while (= res 2)
    (if (not (new_dialog "gip_main" dcl)) (progn (princ $S351) (setq res 0))
      (progn
        (gip:dlg-init S)
        (action_tile "tpl" "(setq S (gip:dlg-read S)) (setq S2 (gip:tpl (gip:g S \"tpl\"))) (foreach k '(\"light\" \"sockets\" \"floor\" \"ac\" \"area\") (setq S (gip:s S k (gip:g S2 k)))) (gip:dlg-set S)")
        (action_tile "b_link" "(setq S (gip:dlg-read S)) (done_dialog 3)")
        (action_tile "b_groups" "(setq S (gip:dlg-read S)) (done_dialog 2)")
        (action_tile "accept" "(setq S (gip:dlg-read S)) (done_dialog 1)")
        (setq res (start_dialog))
        (cond ((= res 2) (setq S (gip:groups-dlg dcl S)))
              ((= res 3) (setq S2 (gip:state-from-link (gip:ask-link)))
                         (if S2 (setq S S2) (princ $S352))
                         (setq res 2))))))
  (unload_dialog dcl)
  (if (= res 1) S))

;; ---------------------------------------------------------------- команды
(defun c:GIPSHCHIT (/ S)
  (setq S (gip:load-state))
  (if (null S) (setq S (gip:default-state "k2")))
  (if (= (gip:g S "v") 2)
    (princ $S353))
  (if (setq S (gip:dialog S))
    (progn
      (if (= (gip:g S "v") 2)
        (setq S (gip:s (gip:s (gip:s (gip:s (gip:s S "v" 1) "rows" nil) "order" nil) "breakAt" nil) "breaks" nil)))
      (gip:run S)))
  (princ))

(defun c:GIPUPD (/ S)
  (if (setq S (gip:load-state))
    (gip:run (gip:sync-from-montage S))
    (princ $S354))
  (princ))

(defun c:GIPLINK (/ S txt)
  (setq txt (gip:ask-link))
  (if (setq S (gip:state-from-link txt)) (gip:run S) (princ $S352))
  (princ))

;; автообновление: после перемещения/удаления/правки атрибутов аппаратов на монтажной схеме
(setq *gip:auto-cmds* '("MOVE" "GRIP_STRETCH" "GRIP_MOVE" "STRETCH" "ERASE" "ATTEDIT" "EATTEDIT" "-ATTEDIT" "PROPERTIES" "COPY" "DELETE" "CUTCLIP" "UNDO" "U" "REDO" "MREDO"))
(defun gip:on-cmd-ended (r args / S)
  (if (and *gip:auto* (not *gip:busy*) (member (strcase (car args)) *gip:auto-cmds*)
           (not (member (strcase (car args)) '("UNDO" "U" "REDO" "MREDO"))))
    (if (and (setq S (gip:load-state)) (gip:montage-changed))
      (progn (princ $S355)
             (setq *gip:in-reactor* T)
             (gip:run (gip:sync-from-montage S))
             (setq *gip:in-reactor* nil)))))
(defun c:GIPAUTO ()
  (setq *gip:auto* (not *gip:auto*))
  (if (and *gip:auto* (null *gip:reactor*))
    (setq *gip:reactor* (vlr-command-reactor nil '((:vlr-commandEnded . gip:on-cmd-ended)))))
  (princ (if *gip:auto* $S356
           $S357))
  (princ))

(defun c:GIPPANELRU () (vla-sendcommand (vla-get-activedocument (vlax-get-acad-object)) "_GIPPANEL ") (princ))

(defun gip:on-load ()
  (setq *gip:protos* nil *gip:ms* nil)
  (if (and (getvar "LISPSYS") (= (getvar "LISPSYS") 0))
    (alert "GIP-SHCHIT: set LISPSYS = 1 and restart AutoCAD (Unicode AutoLISP is required)."))
  (setq *gip:panel-raw* nil)
  (foreach c (list (cons $S358 'c:GIPSHCHIT) (cons $S359 'c:GIPUPD) (cons $S360 'c:GIPLINK) (cons $S361 'c:GIPAUTO) (cons $S362 'c:GIPPANELRU) (cons $S363 'c:GIPPLAN))
    (vl-catch-all-apply 'vlax-add-cmd (list (car c) (cdr c))))
  (setq *gip:auto* T)
  (if (null *gip:reactor*) (setq *gip:reactor* (vlr-command-reactor nil '((:vlr-commandEnded . gip:on-cmd-ended)))))
  (princ $S364)
  (princ $S365)
  (princ $S366)
  (princ))
;;; GIP-ЩИТ: прототипы чертежей (сформировано автоматически из рабочих файлов ГИП)
;;; beta2-style (правки оформления по образцу ГИП, build/patch_protos.py)
(setq *gip:protos-raw* (quote (
 ("frame"
  ("I" "\\U+04103-GIP-ALBOM" 19960.123420928 -10782.462850911 1.0 1.0 0.0 "FORMAT" nil nil "\\U+042D\\U+041E\\U+041C" () ())
 )
 ("head"
  ("I" "A$C594A3AD8" 0.0 0.0 43.357394036 43.357394036 0.0 "\\U+0428\\U+0430\\U+043F\\U+043A\\U+0430 \\U+0449\\U+0438\\U+0442\\U+0430" nil nil nil () ())
 )
 ("st_title"
  ("E" . ((0 . "MTEXT") (100 . "AcDbEntity") (8 . "TEXT") (6 . "Continuous") (62 . 0) (370 . 0) (100 . "AcDbMText") (10 13710.123190859 -10157.462850909 0.0) (40 . 150.0) (41 . 3500.00023007) (46 . 750.0) (71 . 4) (72 . 5) (1 . "\\pxqc;\\U+041F\\U+0440\\U+0438\\U+043D\\U+0446\\U+0438\\U+043F\\U+0438\\U+0430\\U+043B\\U+044C\\U+043D\\U+0430\\U+044F \\U+043E\\U+0434\\U+043D\\U+043E\\U+043B\\U+0438\\U+043D\\U+0435\\U+0439\\U+043D\\U+0430\\U+044F \\U+0441\\U+0445\\U+0435\\U+043C\\U+0430 \\U+0449\\U+0438\\U+0442\\U+0430 \\U+0429\\U+0420 \\U+0447.1") (7 . "ls_200") (73 . 2) (44 . 1.0)))
 )
 ("st_stage"
  ("E" . ((0 . "MTEXT") (100 . "AcDbEntity") (8 . "TEXT") (6 . "Continuous") (62 . 0) (370 . 0) (100 . "AcDbMText") (10 17210.123190859 -9532.462850909 0.0) (40 . 150.0) (41 . 750.00023007) (46 . 500.0) (71 . 4) (72 . 5) (1 . "\\pxqc;\\U+0420") (7 . "ls_200") (73 . 2) (44 . 1.0)))
 )
 ("st_no"
  ("E" . ((0 . "MTEXT") (100 . "AcDbEntity") (8 . "TEXT") (6 . "Continuous") (62 . 0) (370 . 0) (100 . "AcDbMText") (10 17960.123190859 -9532.462850909 0.0) (40 . 150.0) (41 . 850.00023007) (46 . 500.0) (71 . 4) (72 . 5) (1 . "\\pxqc;2") (7 . "ls_200") (73 . 2) (44 . 1.0)))
 )
 ("shr3"
  ("E" . ((0 . "TEXT") (100 . "AcDbEntity") (8 . "0") (370 . 0) (100 . "AcDbText") (10 2682.468940574 262.873980185 0.0) (40 . 86.714788073) (1 . "\\U+0429\\U+0420") (7 . "ls_200") (72 . 1) (11 2771.712909965 262.873980185 0.0) (100 . "AcDbText")))
  ("E" . ((0 . "TEXT") (100 . "AcDbEntity") (8 . "0") (370 . 0) (100 . "AcDbText") (10 2482.105225708 127.638560055 0.0) (40 . 86.714788073) (1 . "400/230 \\U+0412") (7 . "ls_200") (72 . 1) (11 2771.712909965 127.638560055 0.0) (100 . "AcDbText")))
  ("E" . ((0 . "LINE") (100 . "AcDbEntity") (8 . "0") (370 . 0) (100 . "AcDbLine") (10 2491.946911613 231.066597519 0.0) (11 3051.478908317 231.066597519 0.0)))
 )
 ("shr1"
  ("E" . ((0 . "TEXT") (100 . "AcDbEntity") (8 . "0") (370 . 0) (100 . "AcDbText") (10 2582.468940574 262.873980185 0.0) (40 . 86.714788073) (1 . "\\U+0429\\U+0420") (7 . "ls_200") (72 . 1) (11 2671.712909965 262.873980185 0.0) (100 . "AcDbText")))
  ("E" . ((0 . "TEXT") (100 . "AcDbEntity") (8 . "0") (370 . 0) (100 . "AcDbText") (10 2512.30879386 127.638560055 0.0) (40 . 86.714788073) (1 . "230 \\U+0412") (7 . "ls_200") (72 . 1) (11 2671.712909965 127.638560055 0.0) (100 . "AcDbText")))
  ("E" . ((0 . "LINE") (100 . "AcDbEntity") (8 . "0") (370 . 0) (100 . "AcDbLine") (10 2491.946911613 231.066597519 0.0) (11 2851.478908318 231.066597519 0.0)))
 )
 ("lbl3"
  ("E" . ((0 . "TEXT") (100 . "AcDbEntity") (8 . "0") (370 . 0) (100 . "AcDbText") (10 2396.291986467 -1131.705846451 0.0) (40 . 86.714788073) (1 . "~50\\U+0413\\U+0446, 400/230\\U+0412") (7 . "ls_200") (100 . "AcDbText")))
  ("E" . ((0 . "TEXT") (100 . "AcDbEntity") (8 . "0") (370 . 0) (100 . "AcDbText") (10 2391.797329748 -1319.327376986 0.0) (40 . 86.714788073) (1 . "\\U+0410\\U+0412\\U+0421") (7 . "ls_200") (100 . "AcDbText")))
  ("E" . ((0 . "TEXT") (100 . "AcDbEntity") (8 . "0") (370 . 0) (100 . "AcDbText") (10 2390.233276802 -1473.302845884 0.0) (40 . 86.714788073) (1 . "N") (7 . "ls_200") (100 . "AcDbText")))
  ("E" . ((0 . "TEXT") (100 . "AcDbEntity") (8 . "0") (370 . 0) (100 . "AcDbText") (10 2384.871045947 -1603.865888112 0.0) (40 . 86.714788073) (1 . "\\U+0420\\U+0415") (7 . "ls_200") (100 . "AcDbText")))
 )
 ("lbl1"
  ("E" . ((0 . "TEXT") (100 . "AcDbEntity") (8 . "0") (370 . 0) (100 . "AcDbText") (10 2396.291986467 -1131.705846451 0.0) (40 . 86.714788073) (1 . "~50\\U+0413\\U+0446, 230\\U+0412") (7 . "ls_200") (100 . "AcDbText")))
  ("E" . ((0 . "TEXT") (100 . "AcDbEntity") (8 . "0") (370 . 0) (100 . "AcDbText") (10 2391.797329748 -1319.327376986 0.0) (40 . 86.714788073) (1 . "L") (7 . "ls_200") (100 . "AcDbText")))
  ("E" . ((0 . "TEXT") (100 . "AcDbEntity") (8 . "0") (370 . 0) (100 . "AcDbText") (10 2390.233276802 -1473.302845884 0.0) (40 . 86.714788073) (1 . "N") (7 . "ls_200") (100 . "AcDbText")))
  ("E" . ((0 . "TEXT") (100 . "AcDbEntity") (8 . "0") (370 . 0) (100 . "AcDbText") (10 2384.871045947 -1603.865888112 0.0) (40 . 86.714788073) (1 . "\\U+0420\\U+0415") (7 . "ls_200") (100 . "AcDbText")))
 )
 ("lblR3"
  ("E" . ((0 . "TEXT") (100 . "AcDbEntity") (8 . "0") (370 . 0) (100 . "AcDbText") (10 18477.96628295 -1594.140614896 0.0) (40 . 86.714788073) (1 . "\\U+0420\\U+0415") (7 . "ls_200") (100 . "AcDbText")))
  ("E" . ((0 . "TEXT") (100 . "AcDbEntity") (8 . "0") (370 . 0) (100 . "AcDbText") (10 18486.138533593 -1477.424584061 0.0) (40 . 86.714788073) (1 . "N") (7 . "ls_200") (100 . "AcDbText")))
  ("E" . ((0 . "TEXT") (100 . "AcDbEntity") (8 . "0") (370 . 0) (100 . "AcDbText") (10 18492.010653651 -1372.063318344 0.0) (40 . 86.714788073) (1 . "\\U+0410\\U+0412\\U+0421") (7 . "ls_200") (100 . "AcDbText")))
 )
 ("lblR1"
  ("E" . ((0 . "TEXT") (100 . "AcDbEntity") (8 . "0") (370 . 0) (100 . "AcDbText") (10 18477.96628295 -1594.140614896 0.0) (40 . 86.714788073) (1 . "\\U+0420\\U+0415") (7 . "ls_200") (100 . "AcDbText")))
  ("E" . ((0 . "TEXT") (100 . "AcDbEntity") (8 . "0") (370 . 0) (100 . "AcDbText") (10 18486.138533593 -1477.424584061 0.0) (40 . 86.714788073) (1 . "N") (7 . "ls_200") (100 . "AcDbText")))
  ("E" . ((0 . "TEXT") (100 . "AcDbEntity") (8 . "0") (370 . 0) (100 . "AcDbText") (10 18492.010653651 -1372.063318344 0.0) (40 . 86.714788073) (1 . "L") (7 . "ls_200") (100 . "AcDbText")))
 )
 ("busL"
  ("E" . ((0 . "LWPOLYLINE") (100 . "AcDbEntity") (8 . "\\U+0428\\U+0430\\U+043F\\U+043A\\U+0430 \\U+0449\\U+0438\\U+0442\\U+0430") (370 . 0) (100 . "AcDbPolyline") (90 . 2) (70 . 0) (43 . 21.678697018) (10 2551.632914411 -1348.267025244) (10 18448.482183606 -1348.267080189)))
 )
 ("busN"
  ("E" . ((0 . "LINE") (100 . "AcDbEntity") (8 . "\\U+0428\\U+0430\\U+043F\\U+043A\\U+0430 \\U+0449\\U+0438\\U+0442\\U+0430") (370 . 0) (100 . "AcDbLine") (10 2551.632911152 -1437.391206665 0.0) (11 18448.482183606 -1437.391470114 0.0)))
 )
 ("busPE"
  ("E" . ((0 . "LINE") (100 . "AcDbEntity") (8 . "\\U+0428\\U+0430\\U+043F\\U+043A\\U+0430 \\U+0449\\U+0438\\U+0442\\U+0430") (6 . "O2") (48 . 5.0) (370 . 0) (100 . "AcDbLine") (10 2550.515114365 -1527.179094003 0.0) (11 18448.482183606 -1527.179490398 0.0)))
 )
 ("slashL"
  ("E" . ((0 . "LWPOLYLINE") (100 . "AcDbEntity") (8 . "0") (100 . "AcDbPolyline") (90 . 2) (70 . 0) (43 . 0.0) (10 2546.245845543 -1406.517809186) (10 2662.747413427 -1290.016241302)))
  ("E" . ((0 . "LWPOLYLINE") (100 . "AcDbEntity") (8 . "0") (100 . "AcDbPolyline") (90 . 2) (70 . 0) (43 . 0.0) (10 2576.245845543 -1406.517809186) (10 2692.747413427 -1290.016241302)))
  ("E" . ((0 . "LWPOLYLINE") (100 . "AcDbEntity") (8 . "0") (100 . "AcDbPolyline") (90 . 2) (70 . 0) (43 . 0.0) (10 2606.245845543 -1406.517809186) (10 2722.747413427 -1290.016241302)))
 )
 ("slashR"
  ("E" . ((0 . "LWPOLYLINE") (100 . "AcDbEntity") (8 . "0") (100 . "AcDbPolyline") (90 . 2) (70 . 0) (43 . 0.0) (10 18277.36768459 -1406.517864132) (10 18393.869252474 -1290.016296248)))
  ("E" . ((0 . "LWPOLYLINE") (100 . "AcDbEntity") (8 . "0") (100 . "AcDbPolyline") (90 . 2) (70 . 0) (43 . 0.0) (10 18307.36768459 -1406.517864132) (10 18423.869252474 -1290.016296248)))
  ("E" . ((0 . "LWPOLYLINE") (100 . "AcDbEntity") (8 . "0") (100 . "AcDbPolyline") (90 . 2) (70 . 0) (43 . 0.0) (10 18337.36768459 -1406.517864132) (10 18453.869252474 -1290.016296248)))
 )
 ("rectDev"
  ("E" . ((0 . "LWPOLYLINE") (100 . "AcDbEntity") (8 . "0") (6 . "O2") (48 . 2.0) (370 . 0) (100 . "AcDbPolyline") (90 . 5) (70 . 0) (43 . 0.0) (10 2385.491449254 450.0) (10 18771.323925979 450.000090039) (10 18771.323925979 -3175.872900346) (10 2385.491449254 -3175.872983904) (10 2385.491449254 450.0)))
 )
 ("rectTab"
  ("E" . ((0 . "LWPOLYLINE") (100 . "AcDbEntity") (8 . "0") (100 . "AcDbPolyline") (90 . 4) (70 . 0) (43 . 0.0) (10 2385.491449254 -4547.342794136) (10 18167.818075084 -4543.627207379) (10 18167.818075084 -7071.419508423) (10 2385.491449254 -7075.135095179)))
 )
 ("floor3"
  ("E" . ((0 . "ARC") (100 . "AcDbEntity") (8 . "0") (6 . "O2") (48 . 5.0) (370 . 0) (100 . "AcDbCircle") (10 4559.52518809 918.226863933 0.0) (40 . 257.772114079) (100 . "AcDbArc") (50 . 87.893307929) (51 . 175.42226573)))
  ("E" . ((0 . "ARC") (100 . "AcDbEntity") (8 . "0") (370 . 0) (100 . "AcDbCircle") (10 4530.856397007 903.482289185 0.0) (40 . 394.644598684) (100 . "AcDbArc") (50 . 84.783829683) (51 . 174.830096122)))
  ("E" . ((0 . "ARC") (100 . "AcDbEntity") (8 . "0") (370 . 0) (100 . "AcDbCircle") (10 4520.072562508 924.720943277 0.0) (40 . 547.194426765) (100 . "AcDbArc") (50 . 85.108118612) (51 . 178.526212252)))
  ("E" . ((0 . "LINE") (100 . "AcDbEntity") (8 . "0") (370 . 0) (100 . "AcDbLine") (10 4381.775970188 1141.145397423 0.0) (11 4394.602426202 1080.485906963 0.0)))
  ("E" . ((0 . "LWPOLYLINE") (100 . "AcDbEntity") (8 . "0") (370 . 0) (100 . "AcDbPolyline") (90 . 2) (70 . 0) (43 . 0.0) (10 4388.189198195 1110.815652193) (10 3947.928706711 1480.238068219)))
  ("E" . ((0 . "LINE") (100 . "AcDbEntity") (8 . "0") (370 . 0) (100 . "AcDbLine") (10 4269.677454569 1235.207220534 0.0) (11 4282.503910583 1174.547730075 0.0)))
  ("E" . ((0 . "LINE") (100 . "AcDbEntity") (8 . "0") (370 . 0) (100 . "AcDbLine") (10 4133.97055839 1349.078827067 0.0) (11 4146.797014404 1288.419336607 0.0)))
  ("E" . ((0 . "LINE") (100 . "AcDbEntity") (8 . "0") (370 . 0) (100 . "AcDbLine") (10 3947.928706711 1480.238068219 0.0) (11 3110.649369688 1480.238064461 0.0)))
  ("E" . ((0 . "TEXT") (100 . "AcDbEntity") (8 . "Ramka") (370 . 0) (100 . "AcDbText") (10 3099.232493575 1515.58442865 0.0) (40 . 95.669448448) (1 . "\\U+0412\\U+0412\\U+0413\\U+043D\\U+0433LS 5x6") (7 . "ls_200") (100 . "AcDbText")))
  ("E" . ((0 . "LWPOLYLINE") (100 . "AcDbEntity") (8 . "0") (370 . 0) (100 . "AcDbPolyline") (90 . 2) (70 . 0) (43 . 43.357394036) (10 7728.927631497 839.632442399) (10 7728.927631497 2070.642167076)))
  ("E" . ((0 . "LWPOLYLINE") (100 . "AcDbEntity") (8 . "0") (6 . "O2") (48 . 2.0) (370 . 0) (100 . "AcDbPolyline") (90 . 4) (70 . 1) (43 . 0.0) (10 4515.524620963 2168.841526146) (10 7213.932674682 2168.841526146) (10 7213.932674682 1033.523282204) (10 4515.524620963 1033.523282204)))
  ("E" . ((0 . "LWPOLYLINE") (100 . "AcDbEntity") (8 . "0") (100 . "AcDbPolyline") (90 . 2) (70 . 0) (43 . 0.0) (10 7593.090416282 1296.492571468) (10 5997.145704499 1296.492568421)))
  ("I" "\\U+0441\\U+0447\\U+0435\\U+0442\\U+0447\\U+0438\\U+043A1" 5891.91542943 1272.572884947 43.357394036 43.357394036 0.0 "0" nil nil nil () (("\\U+0421\\U+0415\\U+0420\\U+0418\\U+042F" . "\\U+041C\\U+0435\\U+0440\\U+043A\\U+0443\\U+0440\\U+0438\\U+0439 236 ART")))
  ("E" . ((0 . "TEXT") (100 . "AcDbEntity") (8 . "0") (370 . 0) (100 . "AcDbText") (10 4874.108607665 1698.584774847 0.0) (40 . 86.714788073) (1 . "32\\U+0410/100\\U+043C\\U+0410") (7 . "ls_200") (100 . "AcDbText")))
  ("E" . ((0 . "TEXT") (100 . "AcDbEntity") (8 . "0") (370 . 0) (100 . "AcDbText") (10 7692.435033737 2137.598982146 0.0) (40 . 86.714788073) (1 . "\\U+0410,\\U+0412,\\U+0421") (7 . "ls_200") (100 . "AcDbText")))
  ("E" . ((0 . "LINE") (100 . "AcDbEntity") (8 . "0") (370 . 0) (100 . "AcDbLine") (10 7593.090416282 2070.642167076 0.0) (11 7593.090416282 839.632442399 0.0)))
  ("E" . ((0 . "LINE") (100 . "AcDbEntity") (8 . "0") (6 . "O2") (48 . 5.0) (370 . 0) (100 . "AcDbLine") (10 7463.932674682 839.632442399 0.0) (11 7463.932674682 2070.642167076 0.0)))
  ("E" . ((0 . "HATCH") (100 . "AcDbEntity") (8 . "0") (370 . 0) (100 . "AcDbHatch") (10 0.0 0.0 0.0) (210 0.0 0.0 1.0) (2 . "SOLID") (70 . 1) (71 . 0) (91 . 2) (92 . 7) (72 . 1) (73 . 1) (93 . 2) (10 7436.134999713 1175.824750901 0.0) (42 . 0.0) (10 7491.558811467 1175.824750901 0.0) (42 . 1.0) (97 . 0) (92 . 7) (72 . 1) (73 . 1) (93 . 2) (10 7491.558811467 1175.824750901 0.0) (42 . 0.0) (10 7436.134999713 1175.824750901 0.0) (42 . 1.0) (97 . 0) (75 . 0) (76 . 1) (47 . 0.029738707) (98 . 2) (10 7470.296916967 1184.215869365 0.0) (10 7465.136975094 1170.032503628 0.0) (450 . 0) (451 . 0) (460 . 0.0) (461 . 0.0) (452 . 0) (462 . 0.0) (453 . 0) (470 . "")))
  ("E" . ((0 . "HATCH") (100 . "AcDbEntity") (8 . "0") (370 . 0) (100 . "AcDbHatch") (10 0.0 0.0 0.0) (210 0.0 0.0 1.0) (2 . "SOLID") (70 . 1) (71 . 0) (91 . 2) (92 . 7) (72 . 1) (73 . 1) (93 . 2) (10 7436.232060975 1175.824749878 0.0) (42 . 0.0) (10 7491.655872723 1175.824749878 0.0) (42 . 1.0) (97 . 0) (92 . 7) (72 . 1) (73 . 1) (93 . 2) (10 7491.655872723 1175.824749878 0.0) (42 . 0.0) (10 7436.232060975 1175.824749878 0.0) (42 . 1.0) (97 . 0) (75 . 0) (76 . 1) (47 . 0.029738707) (98 . 2) (10 7470.393978222 1184.215868342 0.0) (10 7465.23403635 1170.032502604 0.0) (450 . 0) (451 . 0) (460 . 0.0) (461 . 0.0) (452 . 0) (462 . 0.0) (453 . 0) (470 . "")))
  ("E" . ((0 . "HATCH") (100 . "AcDbEntity") (8 . "0") (370 . 0) (100 . "AcDbHatch") (10 0.0 0.0 0.0) (210 0.0 0.0 1.0) (2 . "SOLID") (70 . 1) (71 . 0) (91 . 2) (92 . 7) (72 . 1) (73 . 1) (93 . 2) (10 7436.21976619 1175.824751925 0.0) (42 . 0.0) (10 7491.643577938 1175.824751925 0.0) (42 . 1.0) (97 . 0) (92 . 7) (72 . 1) (73 . 1) (93 . 2) (10 7491.643577938 1175.824751925 0.0) (42 . 0.0) (10 7436.21976619 1175.824751925 0.0) (42 . 1.0) (97 . 0) (75 . 0) (76 . 1) (47 . 0.029738707) (98 . 2) (10 7470.381683437 1184.215870388 0.0) (10 7465.221741565 1170.032504651 0.0) (450 . 0) (451 . 0) (460 . 0.0) (461 . 0.0) (452 . 0) (462 . 0.0) (453 . 0) (470 . "")))
  ("E" . ((0 . "HATCH") (100 . "AcDbEntity") (8 . "0") (370 . 0) (100 . "AcDbHatch") (10 0.0 0.0 0.0) (210 0.0 0.0 1.0) (2 . "SOLID") (70 . 1) (71 . 0) (91 . 2) (92 . 7) (72 . 1) (73 . 1) (93 . 2) (10 7565.292741314 1296.492561548 0.0) (42 . 0.0) (10 7620.716553062 1296.492561548 0.0) (42 . 1.0) (97 . 0) (92 . 7) (72 . 1) (73 . 1) (93 . 2) (10 7620.716553062 1296.492561548 0.0) (42 . 0.0) (10 7565.292741314 1296.492561548 0.0) (42 . 1.0) (97 . 0) (75 . 0) (76 . 1) (47 . 0.029738707) (98 . 2) (10 7599.454658561 1304.883680012 0.0) (10 7594.294716689 1290.700314275 0.0) (450 . 0) (451 . 0) (460 . 0.0) (461 . 0.0) (452 . 0) (462 . 0.0) (453 . 0) (470 . "")))
  ("E" . ((0 . "HATCH") (100 . "AcDbEntity") (8 . "0") (370 . 0) (100 . "AcDbHatch") (10 0.0 0.0 0.0) (210 0.0 0.0 1.0) (2 . "SOLID") (70 . 1) (71 . 0) (91 . 2) (92 . 7) (72 . 1) (73 . 1) (93 . 2) (10 7565.389802576 1296.492560525 0.0) (42 . 0.0) (10 7620.813614327 1296.492560525 0.0) (42 . 1.0) (97 . 0) (92 . 7) (72 . 1) (73 . 1) (93 . 2) (10 7620.813614327 1296.492560525 0.0) (42 . 0.0) (10 7565.389802576 1296.492560525 0.0) (42 . 1.0) (97 . 0) (75 . 0) (76 . 1) (47 . 0.029738707) (98 . 2) (10 7599.551719824 1304.883678989 0.0) (10 7594.391777951 1290.700313251 0.0) (450 . 0) (451 . 0) (460 . 0.0) (461 . 0.0) (452 . 0) (462 . 0.0) (453 . 0) (470 . "")))
  ("E" . ((0 . "HATCH") (100 . "AcDbEntity") (8 . "0") (370 . 0) (100 . "AcDbHatch") (10 0.0 0.0 0.0) (210 0.0 0.0 1.0) (2 . "SOLID") (70 . 1) (71 . 0) (91 . 2) (92 . 7) (72 . 1) (73 . 1) (93 . 2) (10 7565.377507785 1296.492562571 0.0) (42 . 0.0) (10 7620.801319539 1296.492562571 0.0) (42 . 1.0) (97 . 0) (92 . 7) (72 . 1) (73 . 1) (93 . 2) (10 7620.801319539 1296.492562571 0.0) (42 . 0.0) (10 7565.377507785 1296.492562571 0.0) (42 . 1.0) (97 . 0) (75 . 0) (76 . 1) (47 . 0.029738707) (98 . 2) (10 7599.539425038 1304.883681035 0.0) (10 7594.379483166 1290.700315298 0.0) (450 . 0) (451 . 0) (460 . 0.0) (461 . 0.0) (452 . 0) (462 . 0.0) (453 . 0) (470 . "")))
  ("E" . ((0 . "HATCH") (100 . "AcDbEntity") (8 . "0") (370 . 0) (100 . "AcDbHatch") (10 0.0 0.0 0.0) (210 0.0 0.0 1.0) (2 . "SOLID") (70 . 1) (71 . 0) (91 . 2) (92 . 7) (72 . 1) (73 . 1) (93 . 2) (10 7701.129956528 1469.922153115 0.0) (42 . 0.0) (10 7756.553768276 1469.922153115 0.0) (42 . 1.0) (97 . 0) (92 . 7) (72 . 1) (73 . 1) (93 . 2) (10 7756.553768276 1469.922153115 0.0) (42 . 0.0) (10 7701.129956528 1469.922153115 0.0) (42 . 1.0) (97 . 0) (75 . 0) (76 . 1) (47 . 0.029738707) (98 . 2) (10 7735.291873776 1478.313271579 0.0) (10 7730.131931903 1464.129905842 0.0) (450 . 0) (451 . 0) (460 . 0.0) (461 . 0.0) (452 . 0) (462 . 0.0) (453 . 0) (470 . "")))
  ("E" . ((0 . "HATCH") (100 . "AcDbEntity") (8 . "0") (370 . 0) (100 . "AcDbHatch") (10 0.0 0.0 0.0) (210 0.0 0.0 1.0) (2 . "SOLID") (70 . 1) (71 . 0) (91 . 2) (92 . 7) (72 . 1) (73 . 1) (93 . 2) (10 7701.227017787 1469.922152092 0.0) (42 . 0.0) (10 7756.650829539 1469.922152092 0.0) (42 . 1.0) (97 . 0) (92 . 7) (72 . 1) (73 . 1) (93 . 2) (10 7756.650829539 1469.922152092 0.0) (42 . 0.0) (10 7701.227017787 1469.922152092 0.0) (42 . 1.0) (97 . 0) (75 . 0) (76 . 1) (47 . 0.029738707) (98 . 2) (10 7735.388935038 1478.313270556 0.0) (10 7730.228993165 1464.12990482 0.0) (450 . 0) (451 . 0) (460 . 0.0) (461 . 0.0) (452 . 0) (462 . 0.0) (453 . 0) (470 . "")))
  ("E" . ((0 . "HATCH") (100 . "AcDbEntity") (8 . "0") (370 . 0) (100 . "AcDbHatch") (10 0.0 0.0 0.0) (210 0.0 0.0 1.0) (2 . "SOLID") (70 . 1) (71 . 0) (91 . 2) (92 . 7) (72 . 1) (73 . 1) (93 . 2) (10 7701.214722999 1469.922154139 0.0) (42 . 0.0) (10 7756.638534754 1469.922154139 0.0) (42 . 1.0) (97 . 0) (92 . 7) (72 . 1) (73 . 1) (93 . 2) (10 7756.638534754 1469.922154139 0.0) (42 . 0.0) (10 7701.214722999 1469.922154139 0.0) (42 . 1.0) (97 . 0) (75 . 0) (76 . 1) (47 . 0.029738707) (98 . 2) (10 7735.376640246 1478.313272603 0.0) (10 7730.216698374 1464.129906865 0.0) (450 . 0) (451 . 0) (460 . 0.0) (461 . 0.0) (452 . 0) (462 . 0.0) (453 . 0) (470 . "")))
  ("E" . ((0 . "TEXT") (100 . "AcDbEntity") (8 . "0") (370 . 0) (100 . "AcDbText") (10 7564.204124021 2137.847486328 0.0) (40 . 86.714788073) (1 . "N") (7 . "ls_200") (100 . "AcDbText")))
  ("E" . ((0 . "TEXT") (100 . "AcDbEntity") (8 . "0") (370 . 0) (100 . "AcDbText") (10 7367.310090564 2137.297519912 0.0) (40 . 86.714788073) (1 . "\\U+0420\\U+0415") (7 . "ls_200") (100 . "AcDbText")))
  ("E" . ((0 . "LINE") (100 . "AcDbEntity") (8 . "0") (370 . 0) (100 . "AcDbLine") (10 5280.35874309 1567.873528426 0.0) (11 5066.734974156 1469.92215386 0.0)))
  ("E" . ((0 . "LINE") (100 . "AcDbEntity") (8 . "0") (370 . 0) (100 . "AcDbLine") (10 5280.35874309 1394.443952384 0.0) (11 5066.734974156 1296.492577819 0.0)))
  ("E" . ((0 . "LINE") (100 . "AcDbEntity") (8 . "0") (370 . 0) (100 . "AcDbLine") (10 5193.95405478 1528.255006426 0.0) (11 5193.95405478 1354.825430385 0.0)))
  ("E" . ((0 . "LINE") (100 . "AcDbEntity") (8 . "0") (370 . 0) (100 . "AcDbLine") (10 5138.978483007 1503.047451812 0.0) (11 5138.978483007 1329.61787577 0.0)))
  ("E" . ((0 . "ELLIPSE") (100 . "AcDbEntity") (8 . "0") (370 . 0) (100 . "AcDbEllipse") (10 4982.445691972 1382.524803628 0.0) (11 0.0 173.429576146 0.0) (210 0.0 0.0 1.0) (40 . 0.3) (41 . 0.0) (42 . 6.283185307)))
  ("E" . ((0 . "LINE") (100 . "AcDbEntity") (8 . "0") (6 . "ACAD_ISO03W100") (48 . 0.5) (370 . 0) (100 . "AcDbLine") (10 4982.445691972 1555.954379774 0.0) (11 4982.445691972 1641.468086192 0.0)))
  ("E" . ((0 . "LINE") (100 . "AcDbEntity") (8 . "0") (6 . "ACAD_ISO03W100") (48 . 0.5) (370 . 0) (100 . "AcDbLine") (10 4982.445691972 1641.468086192 0.0) (11 5165.906731045 1641.468086192 0.0)))
  ("E" . ((0 . "LINE") (100 . "AcDbEntity") (8 . "0") (6 . "ACAD_ISO03W100") (48 . 0.5) (370 . 0) (100 . "AcDbLine") (10 5165.906731045 1641.468086192 0.0) (11 5166.466268894 1515.651229119 0.0)))
  ("E" . ((0 . "LINE") (100 . "AcDbEntity") (8 . "0") (370 . 0) (100 . "AcDbLine") (10 5283.521944339 1502.440199388 0.0) (11 5283.521944339 1437.404108333 0.0)))
  ("E" . ((0 . "LINE") (100 . "AcDbEntity") (8 . "0") (370 . 0) (100 . "AcDbLine") (10 5295.622611298 1492.915884363 0.0) (11 5341.610072303 1446.928423356 0.0)))
  ("E" . ((0 . "LINE") (100 . "AcDbEntity") (8 . "0") (370 . 0) (100 . "AcDbLine") (10 5341.610072303 1492.915884363 0.0) (11 5295.622611298 1446.928423356 0.0)))
  ("E" . ((0 . "LINE") (100 . "AcDbEntity") (8 . "0") (370 . 0) (100 . "AcDbLine") (10 5283.521944339 1329.010623347 0.0) (11 5283.521944339 1263.974532292 0.0)))
  ("E" . ((0 . "LINE") (100 . "AcDbEntity") (8 . "0") (370 . 0) (100 . "AcDbLine") (10 5295.622611298 1319.486308322 0.0) (11 5341.610072303 1273.498847315 0.0)))
  ("E" . ((0 . "LINE") (100 . "AcDbEntity") (8 . "0") (370 . 0) (100 . "AcDbLine") (10 5341.610072303 1319.486308322 0.0) (11 5295.622611298 1273.498847315 0.0)))
  ("E" . ((0 . "TEXT") (100 . "AcDbEntity") (8 . "0") (370 . 0) (100 . "AcDbText") (10 5612.836764821 1760.169086595 0.0) (40 . 86.714788073) (1 . "400/230\\U+0412 5-60\\U+0410") (7 . "ls_200") (100 . "AcDbText")))
  ("E" . ((0 . "TEXT") (100 . "AcDbEntity") (8 . "0") (370 . 0) (100 . "AcDbText") (10 4874.108607665 1796.728648373 0.0) (40 . 86.714788073) (1 . "QFD") (7 . "ls_200") (100 . "AcDbText")))
  ("E" . ((0 . "TEXT") (100 . "AcDbEntity") (8 . "0") (370 . 0) (100 . "AcDbText") (10 6620.242261927 1689.769965276 0.0) (40 . 86.714788073) (1 . "QS 40\\U+0410") (7 . "ls_200") (72 . 1) (11 6785.420794602 1689.769965276 0.0) (100 . "AcDbText")))
  ("E" . ((0 . "LINE") (100 . "AcDbEntity") (8 . "0") (370 . 0) (100 . "AcDbLine") (10 6713.932674681 1567.873547551 0.0) (11 6500.308914521 1469.92215386 0.0)))
  ("E" . ((0 . "LINE") (100 . "AcDbEntity") (8 . "0") (370 . 0) (100 . "AcDbLine") (10 6846.659116796 1531.238760989 0.0) (11 6969.292346148 1408.605531639 0.0)))
  ("E" . ((0 . "LINE") (100 . "AcDbEntity") (8 . "0") (370 . 0) (100 . "AcDbLine") (10 6819.650072661 1531.238760989 0.0) (11 6942.28330201 1408.605531639 0.0)))
  ("E" . ((0 . "LINE") (100 . "AcDbEntity") (8 . "0") (370 . 0) (100 . "AcDbLine") (10 6793.761787801 1531.238760989 0.0) (11 6916.395017151 1408.605531639 0.0)))
  ("E" . ((0 . "LINE") (100 . "AcDbEntity") (8 . "0") (6 . "O2") (48 . 5.0) (370 . 0) (100 . "AcDbLine") (10 4569.001001565 1175.824751647 0.0) (11 7463.932674682 1175.824751647 0.0)))
  ("E" . ((0 . "LINE") (100 . "AcDbEntity") (8 . "0") (370 . 0) (100 . "AcDbLine") (10 5416.248386454 1531.238743954 0.0) (11 5538.881615806 1408.605514604 0.0)))
  ("E" . ((0 . "LINE") (100 . "AcDbEntity") (8 . "0") (370 . 0) (100 . "AcDbLine") (10 5389.239342319 1531.238743954 0.0) (11 5511.872571667 1408.605514604 0.0)))
  ("E" . ((0 . "LINE") (100 . "AcDbEntity") (8 . "0") (370 . 0) (100 . "AcDbLine") (10 5363.351057458 1531.238743954 0.0) (11 5485.984286808 1408.605514604 0.0)))
  ("E" . ((0 . "TEXT") (100 . "AcDbEntity") (8 . "0") (370 . 0) (100 . "AcDbText") (10 4559.28156738 2044.03482024 0.0) (40 . 86.714788073) (1 . "\\U+0429\\U+0420 \\U+044D\\U+0442\\U+0430\\U+0436\\U+043D\\U+044B\\U+0439") (7 . "ls_200") (100 . "AcDbText")))
  ("E" . ((0 . "LINE") (100 . "AcDbEntity") (8 . "0") (370 . 0) (100 . "AcDbLine") (10 6713.932674682 1502.440190205 0.0) (11 6713.932674682 1437.40409915 0.0)))
  ("E" . ((0 . "LWPOLYLINE") (100 . "AcDbEntity") (8 . "0") (100 . "AcDbPolyline") (90 . 2) (70 . 0) (43 . 0.0) (10 5283.521944339 1469.92215386) (10 5783.521944339 1469.92215386)))
  ("E" . ((0 . "LWPOLYLINE") (100 . "AcDbEntity") (8 . "0") (100 . "AcDbPolyline") (90 . 2) (70 . 0) (43 . 0.0) (10 5066.734974156 1469.92215386) (10 4566.734974156 1469.92215386)))
  ("E" . ((0 . "LWPOLYLINE") (100 . "AcDbEntity") (8 . "0") (100 . "AcDbPolyline") (90 . 2) (70 . 0) (43 . 0.0) (10 6000.308914521 1469.92215386) (10 6500.308914521 1469.92215386)))
  ("E" . ((0 . "LWPOLYLINE") (100 . "AcDbEntity") (8 . "0") (100 . "AcDbPolyline") (90 . 2) (70 . 0) (43 . 0.0) (10 6713.932674682 1469.922144678) (10 7728.927631497 1469.922144678)))
  ("E" . ((0 . "CIRCLE") (100 . "AcDbEntity") (8 . "0") (370 . 0) (100 . "AcDbCircle") (10 6696.589717067 1469.922144678 0.0) (40 . 17.342957615)))
  ("E" . ((0 . "LINE") (100 . "AcDbEntity") (8 . "0") (370 . 0) (100 . "AcDbLine") (10 5122.880721664 1538.155343513 0.0) (11 5138.978488815 1503.047465825 0.0)))
  ("E" . ((0 . "LINE") (100 . "AcDbEntity") (8 . "0") (370 . 0) (100 . "AcDbLine") (10 5177.856291174 1563.362903049 0.0) (11 5193.954058331 1528.255025361 0.0)))
  ("E" . ((0 . "HATCH") (100 . "AcDbEntity") (8 . "0") (370 . 0) (100 . "AcDbHatch") (10 0.0 0.0 0.0) (210 0.0 0.0 1.0) (2 . "SOLID") (70 . 1) (71 . 0) (91 . 1) (92 . 7) (72 . 0) (73 . 1) (93 . 4) (10 5193.954058331 1528.255025361 0.0) (10 5177.856291174 1563.362903049 0.0) (10 5122.880721664 1538.155343513 0.0) (10 5138.978488815 1503.047465825 0.0) (97 . 0) (75 . 0) (76 . 1) (47 . 0.055772283) (98 . 1) (10 5156.625090287 1531.977072062 0.0) (450 . 0) (451 . 0) (460 . 0.0) (461 . 0.0) (452 . 1) (462 . 1.0) (453 . 2) (463 . 0.0) (63 . 5) (421 . 255) (463 . 1.0) (63 . 7) (421 . 16777215) (470 . "LINEAR")))
  ("E" . ((0 . "LINE") (100 . "AcDbEntity") (8 . "0") (370 . 0) (100 . "AcDbLine") (10 5177.856291174 1563.362903049 0.0) (11 5122.880721664 1538.155343513 0.0)))
  ("E" . ((0 . "LWPOLYLINE") (100 . "AcDbEntity") (8 . "0") (100 . "AcDbPolyline") (90 . 2) (70 . 0) (43 . 0.0) (10 5283.521944339 1296.492577819) (10 5783.521944339 1296.492577819)))
  ("E" . ((0 . "LWPOLYLINE") (100 . "AcDbEntity") (8 . "0") (100 . "AcDbPolyline") (90 . 2) (70 . 0) (43 . 0.0) (10 4566.734974156 1296.492577819) (10 5066.734974156 1296.492577819)))
 )
 ("floor1"
  ("E" . ((0 . "ARC") (100 . "AcDbEntity") (8 . "0") (6 . "O2") (48 . 5.0) (370 . 0) (100 . "AcDbCircle") (10 4559.525188091 918.226863933 0.0) (40 . 257.772114079) (100 . "AcDbArc") (50 . 87.893307929) (51 . 175.42226573)))
  ("E" . ((0 . "ARC") (100 . "AcDbEntity") (8 . "0") (370 . 0) (100 . "AcDbCircle") (10 4530.856397007 903.482289185 0.0) (40 . 394.644598684) (100 . "AcDbArc") (50 . 84.783829683) (51 . 174.830096122)))
  ("E" . ((0 . "ARC") (100 . "AcDbEntity") (8 . "0") (370 . 0) (100 . "AcDbCircle") (10 4520.072562508 924.720943277 0.0) (40 . 547.194426765) (100 . "AcDbArc") (50 . 85.108118612) (51 . 178.526212252)))
  ("E" . ((0 . "LINE") (100 . "AcDbEntity") (8 . "0") (370 . 0) (100 . "AcDbLine") (10 4381.775970188 1141.145397423 0.0) (11 4394.602426202 1080.485906963 0.0)))
  ("E" . ((0 . "LWPOLYLINE") (100 . "AcDbEntity") (8 . "0") (370 . 0) (100 . "AcDbPolyline") (90 . 2) (70 . 0) (43 . 0.0) (10 4388.189198195 1110.815652193) (10 3947.928706711 1480.238068219)))
  ("E" . ((0 . "LINE") (100 . "AcDbEntity") (8 . "0") (370 . 0) (100 . "AcDbLine") (10 4269.677454569 1235.207220534 0.0) (11 4282.503910583 1174.547730075 0.0)))
  ("E" . ((0 . "LINE") (100 . "AcDbEntity") (8 . "0") (370 . 0) (100 . "AcDbLine") (10 4133.97055839 1349.078827067 0.0) (11 4146.797014404 1288.419336607 0.0)))
  ("E" . ((0 . "LINE") (100 . "AcDbEntity") (8 . "0") (370 . 0) (100 . "AcDbLine") (10 3947.928706711 1480.238068219 0.0) (11 3110.649369688 1480.238064461 0.0)))
  ("E" . ((0 . "TEXT") (100 . "AcDbEntity") (8 . "Ramka") (370 . 0) (100 . "AcDbText") (10 3099.232493575 1515.58442865 0.0) (40 . 95.669448448) (1 . "\\U+0412\\U+0412\\U+0413\\U+043D\\U+0433LS 3x16") (7 . "ls_200") (100 . "AcDbText")))
  ("E" . ((0 . "LWPOLYLINE") (100 . "AcDbEntity") (8 . "0") (370 . 0) (100 . "AcDbPolyline") (90 . 2) (70 . 0) (43 . 43.357394036) (10 7728.927631497 839.632442398) (10 7728.927631497 2070.642167076)))
  ("E" . ((0 . "LWPOLYLINE") (100 . "AcDbEntity") (8 . "0") (6 . "O2") (48 . 2.0) (370 . 0) (100 . "AcDbPolyline") (90 . 4) (70 . 1) (43 . 0.0) (10 4515.524620963 2168.841526145) (10 7213.932674682 2168.841526146) (10 7213.932674682 1033.523282204) (10 4515.524620963 1033.523282204)))
  ("E" . ((0 . "LWPOLYLINE") (100 . "AcDbEntity") (8 . "0") (100 . "AcDbPolyline") (90 . 2) (70 . 0) (43 . 0.0) (10 7593.090416282 1296.492571468) (10 5997.145704499 1296.492568421)))
  ("I" "\\U+0441\\U+0447\\U+0435\\U+0442\\U+0447\\U+0438\\U+043A1" 5891.91542943 1272.572884947 43.357394036 43.357394036 0.0 "0" nil nil nil () (("\\U+0421\\U+0415\\U+0420\\U+0418\\U+042F" . "\\U+041C\\U+0435\\U+0440\\U+043A\\U+0443\\U+0440\\U+0438\\U+0439 204 ARTMX2-02")))
  ("E" . ((0 . "TEXT") (100 . "AcDbEntity") (8 . "0") (370 . 0) (100 . "AcDbText") (10 7705.19025902 2120.276388268 0.0) (40 . 86.714788073) (1 . "L") (7 . "ls_200") (72 . 1) (11 7728.927631497 2095.642167076 0.0) (100 . "AcDbText") (73 . 1)))
  ("E" . ((0 . "LINE") (100 . "AcDbEntity") (8 . "0") (370 . 0) (100 . "AcDbLine") (10 7593.090416282 2070.642167076 0.0) (11 7593.090416282 839.632442398 0.0)))
  ("E" . ((0 . "LINE") (100 . "AcDbEntity") (8 . "0") (6 . "O2") (48 . 5.0) (370 . 0) (100 . "AcDbLine") (10 7463.932674682 839.632442398 0.0) (11 7463.932674682 2070.642167076 0.0)))
  ("E" . ((0 . "HATCH") (100 . "AcDbEntity") (8 . "0") (370 . 0) (100 . "AcDbHatch") (10 0.0 0.0 0.0) (210 0.0 0.0 1.0) (2 . "SOLID") (70 . 1) (71 . 0) (91 . 2) (92 . 7) (72 . 1) (73 . 1) (93 . 2) (10 7436.134999713 1175.824750901 0.0) (42 . 0.0) (10 7491.558811467 1175.824750901 0.0) (42 . 1.0) (97 . 0) (92 . 7) (72 . 1) (73 . 1) (93 . 2) (10 7491.558811467 1175.824750901 0.0) (42 . 0.0) (10 7436.134999713 1175.824750901 0.0) (42 . 1.0) (97 . 0) (75 . 0) (76 . 1) (47 . 0.029738707) (98 . 2) (10 7470.296916967 1184.215869365 0.0) (10 7465.136975094 1170.032503628 0.0) (450 . 0) (451 . 0) (460 . 0.0) (461 . 0.0) (452 . 0) (462 . 0.0) (453 . 0) (470 . "")))
  ("E" . ((0 . "HATCH") (100 . "AcDbEntity") (8 . "0") (370 . 0) (100 . "AcDbHatch") (10 0.0 0.0 0.0) (210 0.0 0.0 1.0) (2 . "SOLID") (70 . 1) (71 . 0) (91 . 2) (92 . 7) (72 . 1) (73 . 1) (93 . 2) (10 7436.232060975 1175.824749878 0.0) (42 . 0.0) (10 7491.655872723 1175.824749878 0.0) (42 . 1.0) (97 . 0) (92 . 7) (72 . 1) (73 . 1) (93 . 2) (10 7491.655872723 1175.824749878 0.0) (42 . 0.0) (10 7436.232060975 1175.824749878 0.0) (42 . 1.0) (97 . 0) (75 . 0) (76 . 1) (47 . 0.029738707) (98 . 2) (10 7470.393978223 1184.215868342 0.0) (10 7465.23403635 1170.032502604 0.0) (450 . 0) (451 . 0) (460 . 0.0) (461 . 0.0) (452 . 0) (462 . 0.0) (453 . 0) (470 . "")))
  ("E" . ((0 . "HATCH") (100 . "AcDbEntity") (8 . "0") (370 . 0) (100 . "AcDbHatch") (10 0.0 0.0 0.0) (210 0.0 0.0 1.0) (2 . "SOLID") (70 . 1) (71 . 0) (91 . 2) (92 . 7) (72 . 1) (73 . 1) (93 . 2) (10 7436.21976619 1175.824751925 0.0) (42 . 0.0) (10 7491.643577938 1175.824751925 0.0) (42 . 1.0) (97 . 0) (92 . 7) (72 . 1) (73 . 1) (93 . 2) (10 7491.643577938 1175.824751925 0.0) (42 . 0.0) (10 7436.21976619 1175.824751925 0.0) (42 . 1.0) (97 . 0) (75 . 0) (76 . 1) (47 . 0.029738707) (98 . 2) (10 7470.381683437 1184.215870388 0.0) (10 7465.221741565 1170.032504651 0.0) (450 . 0) (451 . 0) (460 . 0.0) (461 . 0.0) (452 . 0) (462 . 0.0) (453 . 0) (470 . "")))
  ("E" . ((0 . "HATCH") (100 . "AcDbEntity") (8 . "0") (370 . 0) (100 . "AcDbHatch") (10 0.0 0.0 0.0) (210 0.0 0.0 1.0) (2 . "SOLID") (70 . 1) (71 . 0) (91 . 2) (92 . 7) (72 . 1) (73 . 1) (93 . 2) (10 7565.292741314 1296.492561548 0.0) (42 . 0.0) (10 7620.716553062 1296.492561548 0.0) (42 . 1.0) (97 . 0) (92 . 7) (72 . 1) (73 . 1) (93 . 2) (10 7620.716553062 1296.492561548 0.0) (42 . 0.0) (10 7565.292741314 1296.492561548 0.0) (42 . 1.0) (97 . 0) (75 . 0) (76 . 1) (47 . 0.029738707) (98 . 2) (10 7599.454658561 1304.883680012 0.0) (10 7594.294716689 1290.700314275 0.0) (450 . 0) (451 . 0) (460 . 0.0) (461 . 0.0) (452 . 0) (462 . 0.0) (453 . 0) (470 . "")))
  ("E" . ((0 . "HATCH") (100 . "AcDbEntity") (8 . "0") (370 . 0) (100 . "AcDbHatch") (10 0.0 0.0 0.0) (210 0.0 0.0 1.0) (2 . "SOLID") (70 . 1) (71 . 0) (91 . 2) (92 . 7) (72 . 1) (73 . 1) (93 . 2) (10 7565.389802576 1296.492560525 0.0) (42 . 0.0) (10 7620.813614327 1296.492560525 0.0) (42 . 1.0) (97 . 0) (92 . 7) (72 . 1) (73 . 1) (93 . 2) (10 7620.813614327 1296.492560525 0.0) (42 . 0.0) (10 7565.389802576 1296.492560525 0.0) (42 . 1.0) (97 . 0) (75 . 0) (76 . 1) (47 . 0.029738707) (98 . 2) (10 7599.551719824 1304.883678989 0.0) (10 7594.391777951 1290.700313251 0.0) (450 . 0) (451 . 0) (460 . 0.0) (461 . 0.0) (452 . 0) (462 . 0.0) (453 . 0) (470 . "")))
  ("E" . ((0 . "HATCH") (100 . "AcDbEntity") (8 . "0") (370 . 0) (100 . "AcDbHatch") (10 0.0 0.0 0.0) (210 0.0 0.0 1.0) (2 . "SOLID") (70 . 1) (71 . 0) (91 . 2) (92 . 7) (72 . 1) (73 . 1) (93 . 2) (10 7565.377507785 1296.492562571 0.0) (42 . 0.0) (10 7620.801319539 1296.492562571 0.0) (42 . 1.0) (97 . 0) (92 . 7) (72 . 1) (73 . 1) (93 . 2) (10 7620.801319539 1296.492562571 0.0) (42 . 0.0) (10 7565.377507785 1296.492562571 0.0) (42 . 1.0) (97 . 0) (75 . 0) (76 . 1) (47 . 0.029738707) (98 . 2) (10 7599.539425039 1304.883681035 0.0) (10 7594.379483166 1290.700315298 0.0) (450 . 0) (451 . 0) (460 . 0.0) (461 . 0.0) (452 . 0) (462 . 0.0) (453 . 0) (470 . "")))
  ("E" . ((0 . "HATCH") (100 . "AcDbEntity") (8 . "0") (370 . 0) (100 . "AcDbHatch") (10 0.0 0.0 0.0) (210 0.0 0.0 1.0) (2 . "SOLID") (70 . 1) (71 . 0) (91 . 2) (92 . 7) (72 . 1) (73 . 1) (93 . 2) (10 7701.129956528 1469.922153115 0.0) (42 . 0.0) (10 7756.553768276 1469.922153115 0.0) (42 . 1.0) (97 . 0) (92 . 7) (72 . 1) (73 . 1) (93 . 2) (10 7756.553768276 1469.922153115 0.0) (42 . 0.0) (10 7701.129956528 1469.922153115 0.0) (42 . 1.0) (97 . 0) (75 . 0) (76 . 1) (47 . 0.029738707) (98 . 2) (10 7735.291873776 1478.313271579 0.0) (10 7730.131931903 1464.129905842 0.0) (450 . 0) (451 . 0) (460 . 0.0) (461 . 0.0) (452 . 0) (462 . 0.0) (453 . 0) (470 . "")))
  ("E" . ((0 . "HATCH") (100 . "AcDbEntity") (8 . "0") (370 . 0) (100 . "AcDbHatch") (10 0.0 0.0 0.0) (210 0.0 0.0 1.0) (2 . "SOLID") (70 . 1) (71 . 0) (91 . 2) (92 . 7) (72 . 1) (73 . 1) (93 . 2) (10 7701.227017787 1469.922152092 0.0) (42 . 0.0) (10 7756.650829539 1469.922152092 0.0) (42 . 1.0) (97 . 0) (92 . 7) (72 . 1) (73 . 1) (93 . 2) (10 7756.650829539 1469.922152092 0.0) (42 . 0.0) (10 7701.227017787 1469.922152092 0.0) (42 . 1.0) (97 . 0) (75 . 0) (76 . 1) (47 . 0.029738707) (98 . 2) (10 7735.388935038 1478.313270556 0.0) (10 7730.228993165 1464.129904819 0.0) (450 . 0) (451 . 0) (460 . 0.0) (461 . 0.0) (452 . 0) (462 . 0.0) (453 . 0) (470 . "")))
  ("E" . ((0 . "HATCH") (100 . "AcDbEntity") (8 . "0") (370 . 0) (100 . "AcDbHatch") (10 0.0 0.0 0.0) (210 0.0 0.0 1.0) (2 . "SOLID") (70 . 1) (71 . 0) (91 . 2) (92 . 7) (72 . 1) (73 . 1) (93 . 2) (10 7701.214722999 1469.922154139 0.0) (42 . 0.0) (10 7756.638534754 1469.922154139 0.0) (42 . 1.0) (97 . 0) (92 . 7) (72 . 1) (73 . 1) (93 . 2) (10 7756.638534754 1469.922154139 0.0) (42 . 0.0) (10 7701.214722999 1469.922154139 0.0) (42 . 1.0) (97 . 0) (75 . 0) (76 . 1) (47 . 0.029738707) (98 . 2) (10 7735.376640247 1478.313272603 0.0) (10 7730.216698374 1464.129906865 0.0) (450 . 0) (451 . 0) (460 . 0.0) (461 . 0.0) (452 . 0) (462 . 0.0) (453 . 0) (470 . "")))
  ("E" . ((0 . "TEXT") (100 . "AcDbEntity") (8 . "0") (370 . 0) (100 . "AcDbText") (10 7561.246463214 2120.276388268 0.0) (40 . 86.714788073) (1 . "N") (7 . "ls_200") (72 . 1) (11 7593.090416282 2095.642167076 0.0) (100 . "AcDbText") (73 . 1)))
  ("E" . ((0 . "TEXT") (100 . "AcDbEntity") (8 . "0") (370 . 0) (100 . "AcDbText") (10 7410.867184492 2120.276388268 0.0) (40 . 86.714788073) (1 . "\\U+0420\\U+0415") (7 . "ls_200") (72 . 1) (11 7463.932674682 2095.642167076 0.0) (100 . "AcDbText") (73 . 1)))
  ("E" . ((0 . "LINE") (100 . "AcDbEntity") (8 . "0") (370 . 0) (100 . "AcDbLine") (10 5280.35874309 1567.873528426 0.0) (11 5066.734974156 1469.92215386 0.0)))
  ("E" . ((0 . "LINE") (100 . "AcDbEntity") (8 . "0") (370 . 0) (100 . "AcDbLine") (10 5283.521944339 1502.440199387 0.0) (11 5283.521944339 1437.404108333 0.0)))
  ("E" . ((0 . "LINE") (100 . "AcDbEntity") (8 . "0") (370 . 0) (100 . "AcDbLine") (10 5295.622611298 1492.915884363 0.0) (11 5341.610072303 1446.928423356 0.0)))
  ("E" . ((0 . "LINE") (100 . "AcDbEntity") (8 . "0") (370 . 0) (100 . "AcDbLine") (10 5341.610072303 1492.915884363 0.0) (11 5295.622611298 1446.928423356 0.0)))
  ("E" . ((0 . "TEXT") (100 . "AcDbEntity") (8 . "0") (370 . 0) (100 . "AcDbText") (10 5612.836764822 1760.169086595 0.0) (40 . 86.714788073) (1 . "230\\U+0412, 5-100\\U+0410") (7 . "ls_200") (100 . "AcDbText")))
  ("E" . ((0 . "TEXT") (100 . "AcDbEntity") (8 . "0") (370 . 0) (100 . "AcDbText") (10 6623.815962284 1689.769965276 0.0) (40 . 86.714788073) (1 . "QS 63\\U+0410") (7 . "ls_200") (72 . 1) (11 6785.420794602 1689.769965276 0.0) (100 . "AcDbText")))
  ("E" . ((0 . "LINE") (100 . "AcDbEntity") (8 . "0") (370 . 0) (100 . "AcDbLine") (10 6713.932674681 1567.873547551 0.0) (11 6500.308914521 1469.92215386 0.0)))
  ("E" . ((0 . "LINE") (100 . "AcDbEntity") (8 . "0") (370 . 0) (100 . "AcDbLine") (10 6819.650072662 1531.238760989 0.0) (11 6942.28330201 1408.605531639 0.0)))
  ("E" . ((0 . "LINE") (100 . "AcDbEntity") (8 . "0") (6 . "O2") (48 . 5.0) (370 . 0) (100 . "AcDbLine") (10 4569.001001565 1175.824751646 0.0) (11 7463.932674682 1175.824751647 0.0)))
  ("E" . ((0 . "LINE") (100 . "AcDbEntity") (8 . "0") (370 . 0) (100 . "AcDbLine") (10 5389.239342319 1531.238743954 0.0) (11 5511.872571667 1408.605514604 0.0)))
  ("E" . ((0 . "TEXT") (100 . "AcDbEntity") (8 . "0") (370 . 0) (100 . "AcDbText") (10 4559.281567381 2044.03482024 0.0) (40 . 86.714788073) (1 . "\\U+0429\\U+0420 \\U+044D\\U+0442\\U+0430\\U+0436\\U+043D\\U+044B\\U+0439") (7 . "ls_200") (100 . "AcDbText")))
  ("E" . ((0 . "LINE") (100 . "AcDbEntity") (8 . "0") (370 . 0) (100 . "AcDbLine") (10 6713.932674682 1502.440190205 0.0) (11 6713.932674682 1437.40409915 0.0)))
  ("E" . ((0 . "LWPOLYLINE") (100 . "AcDbEntity") (8 . "0") (100 . "AcDbPolyline") (90 . 2) (70 . 0) (43 . 0.0) (10 5283.521944339 1469.92215386) (10 5783.521944339 1469.92215386)))
  ("E" . ((0 . "LWPOLYLINE") (100 . "AcDbEntity") (8 . "0") (100 . "AcDbPolyline") (90 . 2) (70 . 0) (43 . 0.0) (10 5066.734974156 1469.92215386) (10 4566.734974156 1469.92215386)))
  ("E" . ((0 . "LWPOLYLINE") (100 . "AcDbEntity") (8 . "0") (100 . "AcDbPolyline") (90 . 2) (70 . 0) (43 . 0.0) (10 6000.308914521 1469.92215386) (10 6500.308914521 1469.92215386)))
  ("E" . ((0 . "LWPOLYLINE") (100 . "AcDbEntity") (8 . "0") (100 . "AcDbPolyline") (90 . 2) (70 . 0) (43 . 0.0) (10 6713.932674682 1469.922144678) (10 7728.927631497 1469.922144678)))
  ("E" . ((0 . "CIRCLE") (100 . "AcDbEntity") (8 . "0") (370 . 0) (100 . "AcDbCircle") (10 6696.589717067 1469.922144678 0.0) (40 . 17.342957615)))
  ("E" . ((0 . "LINE") (100 . "AcDbEntity") (8 . "0") (370 . 0) (100 . "AcDbLine") (10 5122.880721664 1538.155343513 0.0) (11 5138.978488815 1503.047465825 0.0)))
  ("E" . ((0 . "LINE") (100 . "AcDbEntity") (8 . "0") (370 . 0) (100 . "AcDbLine") (10 5177.856291174 1563.362903049 0.0) (11 5193.954058331 1528.255025361 0.0)))
  ("E" . ((0 . "HATCH") (100 . "AcDbEntity") (8 . "0") (370 . 0) (100 . "AcDbHatch") (10 0.0 0.0 0.0) (210 0.0 0.0 1.0) (2 . "SOLID") (70 . 1) (71 . 0) (91 . 1) (92 . 7) (72 . 0) (73 . 1) (93 . 4) (10 5193.954058331 1528.255025361 0.0) (10 5177.856291174 1563.362903049 0.0) (10 5122.880721664 1538.155343513 0.0) (10 5138.978488815 1503.047465825 0.0) (97 . 0) (75 . 0) (76 . 1) (47 . 0.055772283) (98 . 1) (10 5156.625090287 1531.977072061 0.0) (450 . 0) (451 . 0) (460 . 0.0) (461 . 0.0) (452 . 1) (462 . 1.0) (453 . 2) (463 . 0.0) (63 . 5) (421 . 255) (463 . 1.0) (63 . 7) (421 . 16777215) (470 . "LINEAR")))
  ("E" . ((0 . "LINE") (100 . "AcDbEntity") (8 . "0") (370 . 0) (100 . "AcDbLine") (10 5177.856291174 1563.362903049 0.0) (11 5122.880721664 1538.155343513 0.0)))
  ("E" . ((0 . "LWPOLYLINE") (100 . "AcDbEntity") (8 . "0") (100 . "AcDbPolyline") (90 . 2) (70 . 0) (43 . 0.0) (10 4566.734974156 1296.492577819) (10 5783.521944339 1296.492577819)))
  ("E" . ((0 . "TEXT") (100 . "AcDbEntity") (8 . "0") (370 . 0) (100 . "AcDbText") (10 5015.515726662 1621.369955713 0.0) (40 . 86.714788073) (1 . "QF 63\\U+0410") (7 . "ls_200") (72 . 1) (11 5173.546858623 1621.369955713 0.0) (100 . "AcDbText")))
 )
 ("in3"
  ("I" "\\U+0430\\U+043F\\U+043F\\U+0430\\U+0440\\U+0430\\U+0442 \\U+0443\\U+043F\\U+0440\\U+0430\\U+0432\\U+043B\\U+0435\\U+043D\\U+0438\\U+044F \\U+0438 \\U+0437\\U+0430\\U+0449\\U+0438\\U+0442\\U+044B \\U+0432 \\U+0420\\U+0429" 3973.059145793 168.709355579 41.189524335 41.189524335 0.0 "\\U+0428\\U+0430\\U+043F\\U+043A\\U+0430 \\U+0449\\U+0438\\U+0442\\U+0430" nil nil "\\U+0410\\U+0432\\U+0442\\U+043E\\U+043C\\U+0430\\U+0442\\U+0438\\U+0447\\U+0435\\U+0441\\U+043A\\U+0438\\U+0439 \\U+0432\\U+044B\\U+043A\\U+043B\\U+044E\\U+0447\\U+0430\\U+0442\\U+0435\\U+043B\\U+044C \\U+0442\\U+0440\\U+0435\\U+0445\\U+043F\\U+043E\\U+043B\\U+044E\\U+0441\\U+043D\\U+044B\\U+0439" () (("\\U+041D\\U+041E\\U+041C.\\U+0422\\U+041E\\U+041A,\\U+0410" . "25") ("\\U+041E\\U+0422\\U+041A\\U+041B.\\U+0421\\U+041F\\U+041E\\U+0421\\U+041E\\U+0411\\U+041D\\U+041E\\U+0421\\U+0422\\U+042C,\\U+041A\\U+0410" . "6") ("\\U+0425\\U+0410\\U+0420\\U+0410\\U+041A\\U+0422\\U+0415\\U+0420\\U+0418\\U+0421\\U+0422\\U+0418\\U+041A\\U+0410" . "\\U+0421") ("\\U+041F\\U+0420\\U+041E\\U+0418\\U+0417\\U+0412\\U+041E\\U+0414\\U+0418\\U+0422\\U+0415\\U+041B\\U+042C" . "ABB") ("\\U+0421\\U+0415\\U+0420\\U+0418\\U+042F" . "S203C") ("\\U+041D\\U+041E\\U+041C\\U+0415\\U+0420" . "")))
 )
 ("rel3"
  ("I" "\\U+0430\\U+043F\\U+043F\\U+0430\\U+0440\\U+0430\\U+0442 \\U+0443\\U+043F\\U+0440\\U+0430\\U+0432\\U+043B\\U+0435\\U+043D\\U+0438\\U+044F \\U+0438 \\U+0437\\U+0430\\U+0449\\U+0438\\U+0442\\U+044B \\U+0432 \\U+0420\\U+0429" 3973.059145793 -449.133509441 41.189524335 41.189524335 0.0 "\\U+0428\\U+0430\\U+043F\\U+043A\\U+0430 \\U+0449\\U+0438\\U+0442\\U+0430" nil nil "\\U+0420\\U+0443\\U+0431\\U+0438\\U+043B\\U+044C\\U+043D\\U+0438\\U+043A \\U+0442\\U+0440\\U+0435\\U+0445\\U+043F\\U+043E\\U+043B\\U+044E\\U+0441\\U+043D\\U+044B\\U+0439" () (("\\U+041D\\U+041E\\U+041C.\\U+0422\\U+041E\\U+041A,\\U+0410" . "63") ("\\U+041E\\U+0422\\U+041A\\U+041B.\\U+0421\\U+041F\\U+041E\\U+0421\\U+041E\\U+0411\\U+041D\\U+041E\\U+0421\\U+0422\\U+042C,\\U+041A\\U+0410" . "6") ("\\U+0425\\U+0410\\U+0420\\U+0410\\U+041A\\U+0422\\U+0415\\U+0420\\U+0418\\U+0421\\U+0422\\U+0418\\U+041A\\U+0410" . "\\U+0421") ("\\U+041F\\U+0420\\U+041E\\U+0418\\U+0417\\U+0412\\U+041E\\U+0414\\U+0418\\U+0422\\U+0415\\U+041B\\U+042C" . "ABB") ("\\U+0421\\U+0415\\U+0420\\U+0418\\U+042F" . "\\U+0420\\U+041D-260t x3") ("\\U+041D\\U+041E\\U+041C\\U+0415\\U+0420" . "")))
 )
 ("rel1"
  ("I" "\\U+0430\\U+043F\\U+043F\\U+0430\\U+0440\\U+0430\\U+0442 \\U+0443\\U+043F\\U+0440\\U+0430\\U+0432\\U+043B\\U+0435\\U+043D\\U+0438\\U+044F \\U+0438 \\U+0437\\U+0430\\U+0449\\U+0438\\U+0442\\U+044B \\U+0432 \\U+0420\\U+0429" 3973.059145793 -449.133509441 41.189524335 41.189524335 0.0 "\\U+0428\\U+0430\\U+043F\\U+043A\\U+0430 \\U+0449\\U+0438\\U+0442\\U+0430" nil nil "\\U+0420\\U+0443\\U+0431\\U+0438\\U+043B\\U+044C\\U+043D\\U+0438\\U+043A \\U+043E\\U+0434\\U+043D\\U+043E\\U+043F\\U+043E\\U+043B\\U+044E\\U+0441\\U+043D\\U+044B\\U+0439" () (("\\U+041D\\U+041E\\U+041C.\\U+0422\\U+041E\\U+041A,\\U+0410" . "63") ("\\U+041E\\U+0422\\U+041A\\U+041B.\\U+0421\\U+041F\\U+041E\\U+0421\\U+041E\\U+0411\\U+041D\\U+041E\\U+0421\\U+0422\\U+042C,\\U+041A\\U+0410" . "6") ("\\U+0425\\U+0410\\U+0420\\U+0410\\U+041A\\U+0422\\U+0415\\U+0420\\U+0418\\U+0421\\U+0422\\U+0418\\U+041A\\U+0410" . "\\U+0421") ("\\U+041F\\U+0420\\U+041E\\U+0418\\U+0417\\U+0412\\U+041E\\U+0414\\U+0418\\U+0422\\U+0415\\U+041B\\U+042C" . "ABB") ("\\U+0421\\U+0415\\U+0420\\U+0418\\U+042F" . "\\U+0420\\U+041D-260t") ("\\U+041D\\U+041E\\U+041C\\U+0415\\U+0420" . "")))
 )
 ("ln_Ltop"
  ("E" . ((0 . "LINE") (100 . "AcDbEntity") (8 . "0") (370 . 0) (100 . "AcDbLine") (10 3973.059146256 168.709355579 0.0) (11 3973.059149817 938.794571763 0.0)))
 )
 ("ln_Ntop"
  ("E" . ((0 . "LWPOLYLINE") (100 . "AcDbEntity") (8 . "0") (370 . 0) (100 . "AcDbPolyline") (90 . 2) (70 . 0) (43 . 0.0) (10 4137.817260458 168.709355579) (10 4137.817264492 939.04349813)))
 )
 ("ln_Nbot"
  ("E" . ((0 . "LWPOLYLINE") (100 . "AcDbEntity") (8 . "0") (370 . 0) (100 . "AcDbPolyline") (90 . 2) (70 . 0) (43 . 0.0) (10 4137.817262292 -1437.391232901) (10 4137.817243033 -1066.97637446)))
 )
 ("ln_Lbot"
  ("E" . ((0 . "LWPOLYLINE") (100 . "AcDbEntity") (8 . "0") (370 . 0) (100 . "AcDbPolyline") (90 . 2) (70 . 0) (43 . 0.0) (10 3973.059145793 -1066.97637446) (10 3973.059146916 -1348.267027165)))
 )
 ("ln_PE"
  ("E" . ((0 . "LWPOLYLINE") (100 . "AcDbEntity") (8 . "0") (6 . "O2") (48 . 5.0) (370 . 0) (100 . "AcDbPolyline") (90 . 2) (70 . 0) (43 . 0.0) (10 4302.575376323 -1527.179137688) (10 4302.575374965 938.80005842)))
 )
 ("km3"
  ("E" . ((0 . "LINE") (100 . "AcDbEntity") (8 . "\\U+0428\\U+0430\\U+043F\\U+043A\\U+0430 \\U+0449\\U+0438\\U+0442\\U+0430") (370 . 0) (100 . "AcDbLine") (10 2551.632911152 -1437.391206665 0.0) (11 18448.482183606 -1437.391470114 0.0)))
  ("E" . ((0 . "LINE") (100 . "AcDbEntity") (8 . "\\U+0428\\U+0430\\U+043F\\U+043A\\U+0430 \\U+0449\\U+0438\\U+0442\\U+0430") (6 . "O2") (48 . 5.0) (370 . 0) (100 . "AcDbLine") (10 2550.515114365 -1527.179094003 0.0) (11 18448.482183606 -1527.179490398 0.0)))
  ("E" . ((0 . "LWPOLYLINE") (100 . "AcDbEntity") (8 . "\\U+0428\\U+0430\\U+043F\\U+043A\\U+0430 \\U+0449\\U+0438\\U+0442\\U+0430") (370 . 0) (100 . "AcDbPolyline") (90 . 4) (70 . 1) (43 . 0.0) (10 2703.265180056 -2593.411208338) (10 2953.545296845 -2593.411198103) (10 2953.545296845 -2285.826520396) (10 2703.265180056 -2285.82653063)))
  ("E" . ((0 . "LWPOLYLINE") (100 . "AcDbEntity") (8 . "\\U+0428\\U+0430\\U+043F\\U+043A\\U+0430 \\U+0449\\U+0438\\U+0442\\U+0430") (370 . 0) (100 . "AcDbPolyline") (90 . 2) (70 . 0) (43 . 0.0) (10 2889.14502569 -2285.826523029) (10 2889.145028362 -1348.267025244)))
  ("E" . ((0 . "ARC") (100 . "AcDbEntity") (8 . "\\U+0428\\U+0430\\U+043F\\U+043A\\U+0430 \\U+0449\\U+0438\\U+0442\\U+0430") (370 . 0) (100 . "AcDbCircle") (10 2763.11572007 -2421.995455628 0.0) (40 . 30.162803246) (100 . "AcDbArc") (50 . 119.999999969) (51 . 299.999999969)))
  ("E" . ((0 . "LWPOLYLINE") (100 . "AcDbEntity") (8 . "\\U+0428\\U+0430\\U+043F\\U+043A\\U+0430 \\U+0449\\U+0438\\U+0442\\U+0430") (370 . 0) (100 . "AcDbPolyline") (90 . 4) (70 . 0) (43 . 0.0) (10 2892.728676702 -2562.480892744) (10 2892.728676702 -2693.411198346) (10 3053.545295008 -2693.411198346) (10 3053.545298687 -1619.819197626)))
  ("E" . ((0 . "LWPOLYLINE") (100 . "AcDbEntity") (8 . "\\U+0428\\U+0430\\U+043F\\U+043A\\U+0430 \\U+0449\\U+0438\\U+0442\\U+0430") (370 . 0) (100 . "AcDbPolyline") (90 . 2) (70 . 0) (43 . 0.0) (10 2874.483690659 -2562.480892744) (10 2844.225030914 -2562.480902979)))
  ("E" . ((0 . "LWPOLYLINE") (100 . "AcDbEntity") (8 . "\\U+0428\\U+0430\\U+043F\\U+043A\\U+0430 \\U+0449\\U+0438\\U+0442\\U+0430") (370 . 0) (100 . "AcDbPolyline") (90 . 2) (70 . 0) (43 . 0.0) (10 2874.483690659 -2562.480892744) (10 2941.382642407 -2562.480892744)))
  ("E" . ((0 . "LWPOLYLINE") (100 . "AcDbEntity") (8 . "\\U+0428\\U+0430\\U+043F\\U+043A\\U+0430 \\U+0449\\U+0438\\U+0442\\U+0430") (370 . 0) (100 . "AcDbPolyline") (90 . 2) (70 . 0) (43 . 0.0) (10 2844.225030914 -2562.480902979) (10 2738.378741081 -2379.149751195)))
  ("E" . ((0 . "ARC") (100 . "AcDbEntity") (8 . "\\U+0428\\U+0430\\U+043F\\U+043A\\U+0430 \\U+0449\\U+0438\\U+0442\\U+0430") (370 . 0) (100 . "AcDbCircle") (10 2860.273331563 -2421.995445393 0.0) (40 . 30.162803246) (100 . "AcDbArc") (50 . 119.999999969) (51 . 299.999999969)))
  ("E" . ((0 . "LWPOLYLINE") (100 . "AcDbEntity") (8 . "\\U+0428\\U+0430\\U+043F\\U+043A\\U+0430 \\U+0449\\U+0438\\U+0442\\U+0430") (370 . 0) (100 . "AcDbPolyline") (90 . 2) (70 . 0) (43 . 0.0) (10 2941.382642407 -2562.480892744) (10 2835.536352573 -2379.149740961)))
  ("E" . ((0 . "ARC") (100 . "AcDbEntity") (8 . "\\U+0428\\U+0430\\U+043F\\U+043A\\U+0430 \\U+0449\\U+0438\\U+0442\\U+0430") (370 . 0) (100 . "AcDbCircle") (10 2811.619365858 -2421.995445393 0.0) (40 . 30.162803246) (100 . "AcDbArc") (50 . 119.999999969) (51 . 299.999999969)))
  ("E" . ((0 . "LWPOLYLINE") (100 . "AcDbEntity") (8 . "\\U+0428\\U+0430\\U+043F\\U+043A\\U+0430 \\U+0449\\U+0438\\U+0442\\U+0430") (370 . 0) (100 . "AcDbPolyline") (90 . 2) (70 . 0) (43 . 0.0) (10 2892.728676702 -2562.480892744) (10 2786.882386869 -2379.149740961)))
  ("E" . ((0 . "LWPOLYLINE") (100 . "AcDbEntity") (8 . "0") (100 . "AcDbPolyline") (90 . 4) (70 . 0) (43 . 0.0) (10 2703.265180056 -2285.82653063) (10 2553.265180056 -2285.82653063) (10 2553.265180056 -2593.411208338) (10 2703.265180056 -2593.411208338)))
  ("E" . ((0 . "LWPOLYLINE") (100 . "AcDbEntity") (8 . "\\U+0428\\U+0430\\U+043F\\U+043A\\U+0430 \\U+0449\\U+0438\\U+0442\\U+0430") (370 . 0) (100 . "AcDbPolyline") (90 . 2) (70 . 0) (43 . 0.0) (10 2789.14502569 -2185.826523029) (10 2789.145026149 -2041.774143268)))
  ("E" . ((0 . "LWPOLYLINE") (100 . "AcDbEntity") (8 . "\\U+0428\\U+0430\\U+043F\\U+043A\\U+0430 \\U+0449\\U+0438\\U+0442\\U+0430") (370 . 0) (100 . "AcDbPolyline") (90 . 2) (70 . 0) (43 . 0.0) (10 2789.145026806 -1835.826523029) (10 2789.145028363 -1348.267024898)))
  ("E" . ((0 . "LWPOLYLINE") (100 . "AcDbEntity") (8 . "0") (100 . "AcDbPolyline") (90 . 3) (70 . 0) (43 . 0.0) (10 2789.14502569 -2185.826523029) (10 2628.265180056 -2185.826523029) (10 2628.265180056 -2285.82653063)))
  ("E" . ((0 . "LWPOLYLINE") (100 . "AcDbEntity") (8 . "0") (100 . "AcDbPolyline") (90 . 2) (70 . 0) (43 . 0.0) (10 2628.265180056 -2593.411208338) (10 2628.265180056 -4351.81190656)))
  ("E" . ((0 . "TEXT") (100 . "AcDbEntity") (8 . "\\U+0428\\U+0430\\U+043F\\U+043A\\U+0430 \\U+0449\\U+0438\\U+0442\\U+0430") (370 . 0) (100 . "AcDbText") (10 2690.773581376 -2536.328024484 0.0) (40 . 100.0) (41 . 0.9) (1 . "KM") (50 . 90.0) (7 . "ls_100") (72 . 1) (11 2690.773581376 -2452.998869484 0.0) (100 . "AcDbText")))
  ("E" . ((0 . "LINE") (100 . "AcDbEntity") (8 . "0") (100 . "AcDbLine") (10 2696.091220969 -1838.831564217 0.0) (11 2789.145026806 -2041.774144702 0.0)))
  ("E" . ((0 . "LINE") (100 . "AcDbEntity") (8 . "0") (100 . "AcDbLine") (10 2730.894242865 -1735.394994952 0.0) (11 2847.395810748 -1618.893427068 0.0)))
  ("E" . ((0 . "LINE") (100 . "AcDbEntity") (8 . "0") (100 . "AcDbLine") (10 2724.32350858 -1988.435687102 0.0) (11 2757.675993752 -1973.142811294 0.0)))
  ("E" . ((0 . "LINE") (100 . "AcDbEntity") (8 . "0") (100 . "AcDbLine") (10 2700.376331696 -1936.20889392 0.0) (11 2733.728816868 -1920.916018113 0.0)))
  ("E" . ((0 . "LINE") (100 . "AcDbEntity") (8 . "0") (100 . "AcDbLine") (10 2758.252883556 -1835.826523029 0.0) (11 2820.037170058 -1835.826523029 0.0)))
  ("E" . ((0 . "LINE") (100 . "AcDbEntity") (8 . "0") (100 . "AcDbLine") (10 2767.300982829 -1824.330889421 0.0) (11 2810.989070785 -1780.642801464 0.0)))
  ("E" . ((0 . "LINE") (100 . "AcDbEntity") (8 . "0") (100 . "AcDbLine") (10 2767.300982829 -1780.642801464 0.0) (11 2810.989070785 -1824.330889421 0.0)))
  ("E" . ((0 . "HATCH") (100 . "AcDbEntity") (8 . "0") (100 . "AcDbHatch") (10 0.0 0.0 0.0) (210 0.0 0.0 1.0) (2 . "SOLID") (70 . 1) (71 . 0) (91 . 1) (92 . 7) (72 . 0) (73 . 1) (93 . 4) (10 2733.728816868 -1920.916018113 0.0) (10 2700.376331696 -1936.20889392 0.0) (10 2724.32350858 -1988.435687102 0.0) (10 2757.675993752 -1973.142811294 0.0) (97 . 0) (75 . 0) (76 . 1) (47 . 0.055772283) (98 . 1) (10 2730.192869328 -1956.378537435 0.0) (450 . 0) (451 . 0) (460 . 0.0) (461 . 0.0) (452 . 1) (462 . 1.0) (453 . 2) (463 . 0.0) (63 . 5) (421 . 255) (463 . 1.0) (63 . 7) (421 . 16777215) (470 . "LINEAR")))
  ("E" . ((0 . "TEXT") (100 . "AcDbEntity") (8 . "0") (100 . "AcDbText") (10 2602.045177266 -1835.264229493 0.0) (40 . 94.73590597) (1 . "\\U+0410") (51 . 15.0) (7 . "style1") (72 . 1) (11 2641.110218412 -1787.896276508 0.0) (100 . "AcDbText") (73 . 2)))
  ("E" . ((0 . "ATTDEF") (100 . "AcDbEntity") (8 . "0") (100 . "AcDbText") (10 2522.784922254 -1837.002092103 0.0) (40 . 94.73590597) (1 . "16") (51 . 15.0) (7 . "style1") (72 . 2) (11 2593.916381538 -1837.002092103 0.0) (100 . "AcDbAttributeDefinition") (280 . 0) (3 . "\\U+041D\\U+043E\\U+043C\\U+0438\\U+043D\\U+0430\\U+043B, \\U+0410") (2 . "2") (70 . 4) (280 . 1)))
  ("E" . ((0 . "LINE") (100 . "AcDbEntity") (8 . "0") (100 . "AcDbLine") (10 2700.376331696 -1936.20889392 0.0) (11 2724.32350858 -1988.435687102 0.0)))
  ("E" . ((0 . "LWPOLYLINE") (100 . "AcDbEntity") (8 . "0") (100 . "AcDbPolyline") (90 . 5) (70 . 0) (43 . 0.0) (10 2628.265180056 -4351.81190656) (10 2478.265180056 -4351.81190656) (10 2478.265180056 -1679.90213038) (10 2628.265180056 -1679.90213038) (10 2628.265180056 -1437.391206768)))
  ("I" "\\U+0412\\U+044B\\U+043A\\U+043B\\U+044E\\U+0447\\U+0430\\U+0442\\U+0435\\U+043B\\U+044C \\U+0441\\U+043A\\U+0440\\U+044B\\U+0442\\U+043E\\U+0439 \\U+0443\\U+0441\\U+0442\\U+0430\\U+043D\\U+043E\\U+0432\\U+043A\\U+0438" 2670.597986823 -4314.38576328 -56.504714223 56.504714223 131.479677064 "\\U+0441\\U+0432\\U+0435\\U+0442\\U+0438\\U+043B\\U+044C\\U+043D\\U+0438\\U+043A\\U+0438" 1 nil "\\U+0432\\U+044B\\U+043A\\U+043B\\U+044E\\U+0447\\U+0430\\U+0442\\U+0435\\U+043B\\U+044C \\U+043E\\U+0434\\U+043D\\U+043E\\U+043A\\U+043B\\U+0430\\U+0432\\U+0438\\U+0448\\U+043D\\U+044B\\U+0439 \\U+043E\\U+0434\\U+043D\\U+043E\\U+043F\\U+043E\\U+043B\\U+044E\\U+0441\\U+043D\\U+044B\\U+0439, 16\\U+0410" () ())
  ("I" "A$C410E7F00" 2628.265180056 -1437.391206768 43.357394032 43.357394032 0.0 "\\U+0428\\U+0430\\U+043F\\U+043A\\U+0430 \\U+0449\\U+0438\\U+0442\\U+0430" nil nil nil () ())
  ("I" "A$C410E7F00" 2789.145028363 -1348.267024898 43.357394032 43.357394032 0.0 "\\U+0428\\U+0430\\U+043F\\U+043A\\U+0430 \\U+0449\\U+0438\\U+0442\\U+0430" nil nil nil () ())
  ("I" "A$C410E7F00" 2889.145028362 -1348.267025244 43.357394032 43.357394032 0.0 "\\U+0428\\U+0430\\U+043F\\U+043A\\U+0430 \\U+0449\\U+0438\\U+0442\\U+0430" nil nil nil () ())
  ("I" "A$C410E7F00" 3053.545298687 -1619.819197626 43.357394032 43.357394032 0.0 "\\U+0428\\U+0430\\U+043F\\U+043A\\U+0430 \\U+0449\\U+0438\\U+0442\\U+0430" nil nil nil () ())
  ("E" . ((0 . "TEXT") (100 . "AcDbEntity") (8 . "\\U+0428\\U+0430\\U+043F\\U+043A\\U+0430 \\U+0449\\U+0438\\U+0442\\U+0430") (370 . 0) (100 . "AcDbText") (10 2681.89226942 -2867.519307542 0.0) (40 . 100.0) (41 . 0.9) (1 . "ESB") (7 . "ls_100") (100 . "AcDbText")))
  ("E" . ((0 . "TEXT") (100 . "AcDbEntity") (8 . "\\U+0428\\U+0430\\U+043F\\U+043A\\U+0430 \\U+0449\\U+0438\\U+0442\\U+0430") (370 . 0) (100 . "AcDbText") (10 2681.89226942 -3017.519307542 0.0) (40 . 100.0) (41 . 0.9) (1 . "63-40N") (7 . "ls_100") (100 . "AcDbText")))
  ("E" . ((0 . "LWPOLYLINE") (100 . "AcDbEntity") (8 . "0") (100 . "AcDbPolyline") (90 . 2) (70 . 0) (43 . 0.0) (10 3090.294514745 -1678.069981568) (10 3206.796082629 -1561.568413685)))
  ("E" . ((0 . "LWPOLYLINE") (100 . "AcDbEntity") (8 . "0") (100 . "AcDbPolyline") (90 . 2) (70 . 0) (43 . 0.0) (10 3120.294514745 -1678.069981568) (10 3236.796082629 -1561.568413685)))
  ("E" . ((0 . "LWPOLYLINE") (100 . "AcDbEntity") (8 . "0") (100 . "AcDbPolyline") (90 . 2) (70 . 0) (43 . 0.0) (10 3150.294514745 -1678.069981568) (10 3266.796082629 -1561.568413685)))
 )
 ("km1"
  ("E" . ((0 . "LINE") (100 . "AcDbEntity") (8 . "\\U+0428\\U+0430\\U+043F\\U+043A\\U+0430 \\U+0449\\U+0438\\U+0442\\U+0430") (370 . 0) (100 . "AcDbLine") (10 2551.632911152 -1437.391206665 0.0) (11 18448.482183606 -1437.391470114 0.0)))
  ("E" . ((0 . "LINE") (100 . "AcDbEntity") (8 . "\\U+0428\\U+0430\\U+043F\\U+043A\\U+0430 \\U+0449\\U+0438\\U+0442\\U+0430") (6 . "O2") (48 . 5.0) (370 . 0) (100 . "AcDbLine") (10 2550.515114365 -1527.179094003 0.0) (11 18448.482183606 -1527.179490398 0.0)))
  ("E" . ((0 . "LWPOLYLINE") (100 . "AcDbEntity") (8 . "\\U+0428\\U+0430\\U+043F\\U+043A\\U+0430 \\U+0449\\U+0438\\U+0442\\U+0430") (370 . 0) (100 . "AcDbPolyline") (90 . 4) (70 . 1) (43 . 0.0) (10 2703.265180056 -2593.411208338) (10 2953.545296845 -2593.411198103) (10 2953.545296845 -2285.826520396) (10 2703.265180056 -2285.826530631)))
  ("E" . ((0 . "LWPOLYLINE") (100 . "AcDbEntity") (8 . "\\U+0428\\U+0430\\U+043F\\U+043A\\U+0430 \\U+0449\\U+0438\\U+0442\\U+0430") (370 . 0) (100 . "AcDbPolyline") (90 . 2) (70 . 0) (43 . 0.0) (10 2889.14502569 -2285.826523029) (10 2889.145028362 -1348.267025244)))
  ("E" . ((0 . "ARC") (100 . "AcDbEntity") (8 . "\\U+0428\\U+0430\\U+043F\\U+043A\\U+0430 \\U+0449\\U+0438\\U+0442\\U+0430") (370 . 0) (100 . "AcDbCircle") (10 2763.11572007 -2421.995455628 0.0) (40 . 30.162803246) (100 . "AcDbArc") (50 . 119.999999969) (51 . 299.999999969)))
  ("E" . ((0 . "LWPOLYLINE") (100 . "AcDbEntity") (8 . "\\U+0428\\U+0430\\U+043F\\U+043A\\U+0430 \\U+0449\\U+0438\\U+0442\\U+0430") (370 . 0) (100 . "AcDbPolyline") (90 . 4) (70 . 0) (43 . 0.0) (10 2892.728676702 -2562.480892744) (10 2892.728676702 -2693.411198347) (10 3053.545295008 -2693.411198347) (10 3053.545298687 -1619.819197626)))
  ("E" . ((0 . "LWPOLYLINE") (100 . "AcDbEntity") (8 . "\\U+0428\\U+0430\\U+043F\\U+043A\\U+0430 \\U+0449\\U+0438\\U+0442\\U+0430") (370 . 0) (100 . "AcDbPolyline") (90 . 2) (70 . 0) (43 . 0.0) (10 2874.483690659 -2562.480892744) (10 2844.225030914 -2562.480902979)))
  ("E" . ((0 . "LWPOLYLINE") (100 . "AcDbEntity") (8 . "\\U+0428\\U+0430\\U+043F\\U+043A\\U+0430 \\U+0449\\U+0438\\U+0442\\U+0430") (370 . 0) (100 . "AcDbPolyline") (90 . 2) (70 . 0) (43 . 0.0) (10 2874.483690659 -2562.480892744) (10 2941.382642407 -2562.480892744)))
  ("E" . ((0 . "LWPOLYLINE") (100 . "AcDbEntity") (8 . "\\U+0428\\U+0430\\U+043F\\U+043A\\U+0430 \\U+0449\\U+0438\\U+0442\\U+0430") (370 . 0) (100 . "AcDbPolyline") (90 . 2) (70 . 0) (43 . 0.0) (10 2844.225030914 -2562.480902979) (10 2738.378741081 -2379.149751195)))
  ("E" . ((0 . "ARC") (100 . "AcDbEntity") (8 . "\\U+0428\\U+0430\\U+043F\\U+043A\\U+0430 \\U+0449\\U+0438\\U+0442\\U+0430") (370 . 0) (100 . "AcDbCircle") (10 2860.273331563 -2421.995445393 0.0) (40 . 30.162803246) (100 . "AcDbArc") (50 . 119.999999969) (51 . 299.999999969)))
  ("E" . ((0 . "LWPOLYLINE") (100 . "AcDbEntity") (8 . "\\U+0428\\U+0430\\U+043F\\U+043A\\U+0430 \\U+0449\\U+0438\\U+0442\\U+0430") (370 . 0) (100 . "AcDbPolyline") (90 . 2) (70 . 0) (43 . 0.0) (10 2941.382642407 -2562.480892744) (10 2835.536352574 -2379.149740961)))
  ("E" . ((0 . "ARC") (100 . "AcDbEntity") (8 . "\\U+0428\\U+0430\\U+043F\\U+043A\\U+0430 \\U+0449\\U+0438\\U+0442\\U+0430") (370 . 0) (100 . "AcDbCircle") (10 2811.619365858 -2421.995445393 0.0) (40 . 30.162803246) (100 . "AcDbArc") (50 . 119.999999969) (51 . 299.999999969)))
  ("E" . ((0 . "LWPOLYLINE") (100 . "AcDbEntity") (8 . "\\U+0428\\U+0430\\U+043F\\U+043A\\U+0430 \\U+0449\\U+0438\\U+0442\\U+0430") (370 . 0) (100 . "AcDbPolyline") (90 . 2) (70 . 0) (43 . 0.0) (10 2892.728676702 -2562.480892744) (10 2786.882386869 -2379.149740961)))
  ("E" . ((0 . "LWPOLYLINE") (100 . "AcDbEntity") (8 . "0") (100 . "AcDbPolyline") (90 . 4) (70 . 0) (43 . 0.0) (10 2703.265180056 -2285.826530631) (10 2553.265180056 -2285.826530631) (10 2553.265180056 -2593.411208338) (10 2703.265180056 -2593.411208338)))
  ("E" . ((0 . "LWPOLYLINE") (100 . "AcDbEntity") (8 . "\\U+0428\\U+0430\\U+043F\\U+043A\\U+0430 \\U+0449\\U+0438\\U+0442\\U+0430") (370 . 0) (100 . "AcDbPolyline") (90 . 2) (70 . 0) (43 . 0.0) (10 2789.14502569 -2185.826523029) (10 2789.145026149 -2041.774143269)))
  ("E" . ((0 . "LWPOLYLINE") (100 . "AcDbEntity") (8 . "\\U+0428\\U+0430\\U+043F\\U+043A\\U+0430 \\U+0449\\U+0438\\U+0442\\U+0430") (370 . 0) (100 . "AcDbPolyline") (90 . 2) (70 . 0) (43 . 0.0) (10 2789.145026806 -1835.826523029) (10 2789.145028363 -1348.267024898)))
  ("E" . ((0 . "LWPOLYLINE") (100 . "AcDbEntity") (8 . "0") (100 . "AcDbPolyline") (90 . 3) (70 . 0) (43 . 0.0) (10 2789.14502569 -2185.826523029) (10 2628.265180056 -2185.826523029) (10 2628.265180056 -2285.826530631)))
  ("E" . ((0 . "LWPOLYLINE") (100 . "AcDbEntity") (8 . "0") (100 . "AcDbPolyline") (90 . 2) (70 . 0) (43 . 0.0) (10 2628.265180056 -2593.411208338) (10 2628.265180056 -4351.81190656)))
  ("E" . ((0 . "TEXT") (100 . "AcDbEntity") (8 . "\\U+0428\\U+0430\\U+043F\\U+043A\\U+0430 \\U+0449\\U+0438\\U+0442\\U+0430") (370 . 0) (100 . "AcDbText") (10 2690.773581376 -2536.328024484 0.0) (40 . 100.0) (41 . 0.9) (1 . "KM") (50 . 90.0) (7 . "ls_100") (72 . 1) (11 2690.773581376 -2452.998869484 0.0) (100 . "AcDbText")))
  ("E" . ((0 . "LINE") (100 . "AcDbEntity") (8 . "0") (100 . "AcDbLine") (10 2696.091220969 -1838.831564217 0.0) (11 2789.145026806 -2041.774144702 0.0)))
  ("E" . ((0 . "LINE") (100 . "AcDbEntity") (8 . "0") (100 . "AcDbLine") (10 2730.894242865 -1735.394994952 0.0) (11 2847.395810748 -1618.893427068 0.0)))
  ("E" . ((0 . "LINE") (100 . "AcDbEntity") (8 . "0") (100 . "AcDbLine") (10 2724.32350858 -1988.435687102 0.0) (11 2757.675993752 -1973.142811294 0.0)))
  ("E" . ((0 . "LINE") (100 . "AcDbEntity") (8 . "0") (100 . "AcDbLine") (10 2700.376331696 -1936.208893921 0.0) (11 2733.728816868 -1920.916018113 0.0)))
  ("E" . ((0 . "LINE") (100 . "AcDbEntity") (8 . "0") (100 . "AcDbLine") (10 2758.252883556 -1835.826523029 0.0) (11 2820.037170058 -1835.826523029 0.0)))
  ("E" . ((0 . "LINE") (100 . "AcDbEntity") (8 . "0") (100 . "AcDbLine") (10 2767.300982829 -1824.330889421 0.0) (11 2810.989070785 -1780.642801464 0.0)))
  ("E" . ((0 . "LINE") (100 . "AcDbEntity") (8 . "0") (100 . "AcDbLine") (10 2767.300982829 -1780.642801464 0.0) (11 2810.989070785 -1824.330889421 0.0)))
  ("E" . ((0 . "HATCH") (100 . "AcDbEntity") (8 . "0") (100 . "AcDbHatch") (10 0.0 0.0 0.0) (210 0.0 0.0 1.0) (2 . "SOLID") (70 . 1) (71 . 0) (91 . 1) (92 . 7) (72 . 0) (73 . 1) (93 . 4) (10 2733.728816868 -1920.916018113 0.0) (10 2700.376331696 -1936.208893921 0.0) (10 2724.32350858 -1988.435687102 0.0) (10 2757.675993752 -1973.142811294 0.0) (97 . 0) (75 . 0) (76 . 1) (47 . 0.055772283) (98 . 1) (10 2730.192869328 -1956.378537435 0.0) (450 . 0) (451 . 0) (460 . 0.0) (461 . 0.0) (452 . 1) (462 . 1.0) (453 . 2) (463 . 0.0) (63 . 5) (421 . 255) (463 . 1.0) (63 . 7) (421 . 16777215) (470 . "LINEAR")))
  ("E" . ((0 . "TEXT") (100 . "AcDbEntity") (8 . "0") (100 . "AcDbText") (10 2602.045177267 -1835.264229493 0.0) (40 . 94.73590597) (1 . "\\U+0410") (51 . 15.0) (7 . "style1") (72 . 1) (11 2641.110218412 -1787.896276508 0.0) (100 . "AcDbText") (73 . 2)))
  ("E" . ((0 . "ATTDEF") (100 . "AcDbEntity") (8 . "0") (100 . "AcDbText") (10 2522.784922254 -1837.002092103 0.0) (40 . 94.73590597) (1 . "16") (51 . 15.0) (7 . "style1") (72 . 2) (11 2593.916381538 -1837.002092103 0.0) (100 . "AcDbAttributeDefinition") (280 . 0) (3 . "\\U+041D\\U+043E\\U+043C\\U+0438\\U+043D\\U+0430\\U+043B, \\U+0410") (2 . "2") (70 . 4) (280 . 1)))
  ("E" . ((0 . "LINE") (100 . "AcDbEntity") (8 . "0") (100 . "AcDbLine") (10 2700.376331696 -1936.208893921 0.0) (11 2724.32350858 -1988.435687102 0.0)))
  ("E" . ((0 . "LWPOLYLINE") (100 . "AcDbEntity") (8 . "0") (100 . "AcDbPolyline") (90 . 5) (70 . 0) (43 . 0.0) (10 2628.265180056 -4351.81190656) (10 2478.265180056 -4351.81190656) (10 2478.265180056 -1679.90213038) (10 2628.265180056 -1679.90213038) (10 2628.265180056 -1437.391206768)))
  ("I" "\\U+0412\\U+044B\\U+043A\\U+043B\\U+044E\\U+0447\\U+0430\\U+0442\\U+0435\\U+043B\\U+044C \\U+0441\\U+043A\\U+0440\\U+044B\\U+0442\\U+043E\\U+0439 \\U+0443\\U+0441\\U+0442\\U+0430\\U+043D\\U+043E\\U+0432\\U+043A\\U+0438" 2670.597986823 -4314.38576328 -56.504714223 56.504714223 131.479677064 "\\U+0441\\U+0432\\U+0435\\U+0442\\U+0438\\U+043B\\U+044C\\U+043D\\U+0438\\U+043A\\U+0438" 1 nil "\\U+0432\\U+044B\\U+043A\\U+043B\\U+044E\\U+0447\\U+0430\\U+0442\\U+0435\\U+043B\\U+044C \\U+043E\\U+0434\\U+043D\\U+043E\\U+043A\\U+043B\\U+0430\\U+0432\\U+0438\\U+0448\\U+043D\\U+044B\\U+0439 \\U+043E\\U+0434\\U+043D\\U+043E\\U+043F\\U+043E\\U+043B\\U+044E\\U+0441\\U+043D\\U+044B\\U+0439, 16\\U+0410" () ())
  ("I" "A$C410E7F00" 2628.265180056 -1437.391206768 43.357394032 43.357394032 0.0 "\\U+0428\\U+0430\\U+043F\\U+043A\\U+0430 \\U+0449\\U+0438\\U+0442\\U+0430" nil nil nil () ())
  ("I" "A$C410E7F00" 2789.145028363 -1348.267024898 43.357394032 43.357394032 0.0 "\\U+0428\\U+0430\\U+043F\\U+043A\\U+0430 \\U+0449\\U+0438\\U+0442\\U+0430" nil nil nil () ())
  ("I" "A$C410E7F00" 2889.145028362 -1348.267025244 43.357394032 43.357394032 0.0 "\\U+0428\\U+0430\\U+043F\\U+043A\\U+0430 \\U+0449\\U+0438\\U+0442\\U+0430" nil nil nil () ())
  ("I" "A$C410E7F00" 3053.545298687 -1619.819197626 43.357394032 43.357394032 0.0 "\\U+0428\\U+0430\\U+043F\\U+043A\\U+0430 \\U+0449\\U+0438\\U+0442\\U+0430" nil nil nil () ())
  ("E" . ((0 . "TEXT") (100 . "AcDbEntity") (8 . "\\U+0428\\U+0430\\U+043F\\U+043A\\U+0430 \\U+0449\\U+0438\\U+0442\\U+0430") (370 . 0) (100 . "AcDbText") (10 2681.89226942 -2867.519307542 0.0) (40 . 100.0) (41 . 0.9) (1 . "ESB") (7 . "ls_100") (100 . "AcDbText")))
  ("E" . ((0 . "TEXT") (100 . "AcDbEntity") (8 . "\\U+0428\\U+0430\\U+043F\\U+043A\\U+0430 \\U+0449\\U+0438\\U+0442\\U+0430") (370 . 0) (100 . "AcDbText") (10 2681.89226942 -3017.519307542 0.0) (40 . 100.0) (41 . 0.9) (1 . "63-40N") (7 . "ls_100") (100 . "AcDbText")))
  ("E" . ((0 . "LWPOLYLINE") (100 . "AcDbEntity") (8 . "0") (100 . "AcDbPolyline") (90 . 2) (70 . 0) (43 . 0.0) (10 3120.294514745 -1678.069981568) (10 3236.796082629 -1561.568413685)))
 )
 ("lightbus"
  ("E" . ((0 . "LWPOLYLINE") (100 . "AcDbEntity") (8 . "\\U+0428\\U+0430\\U+043F\\U+043A\\U+0430 \\U+0449\\U+0438\\U+0442\\U+0430") (100 . "AcDbPolyline") (90 . 2) (70 . 0) (43 . 21.678666667) (10 3053.545298687 -1619.819197626) (10 5986.282084364 -1619.819197626)))
 )
 ("kmname"
  ("E" . ((0 . "MTEXT") (100 . "AcDbEntity") (8 . "0") (370 . 0) (100 . "AcDbMText") (10 2537.584954474 -7022.470192961 0.0) (40 . 120.0) (41 . 2493.87862559) (46 . 496.354736951) (71 . 1) (72 . 5) (1 . "\\pxsm1;{\\T0.9;\\U+041E\\U+0431\\U+0449\\U+0438\\U+0439 \\U+0432\\U+044B\\U+043A\\U+043B\\U+044E\\U+0447\\U+0430\\U+0442\\U+0435\\U+043B\\U+044C\\P\\U+043E\\U+0441\\U+0432\\U+0435\\U+0449\\U+0435\\U+043D\\U+0438\\U+044F}") (7 . "ls_100") (11 0.0 1.0 0.0) (73 . 1) (44 . 1.0)))
 )
 ("dev_a1"
  ("I" "\\U+0430\\U+043F\\U+043F\\U+0430\\U+0440\\U+0430\\U+0442 \\U+0443\\U+043F\\U+0440\\U+0430\\U+0432\\U+043B\\U+0435\\U+043D\\U+0438\\U+044F \\U+0438 \\U+0437\\U+0430\\U+0449\\U+0438\\U+0442\\U+044B \\U+0432 \\U+0420\\U+0429" 0.0 0.0 41.189524335 41.189524335 0.0 "\\U+0428\\U+0430\\U+043F\\U+043A\\U+0430 \\U+0449\\U+0438\\U+0442\\U+0430" nil nil "\\U+0410\\U+0432\\U+0442\\U+043E\\U+043C\\U+0430\\U+0442\\U+0438\\U+0447\\U+0435\\U+0441\\U+043A\\U+0438\\U+0439 \\U+0432\\U+044B\\U+043A\\U+043B\\U+044E\\U+0447\\U+0430\\U+0442\\U+0435\\U+043B\\U+044C \\U+043E\\U+0434\\U+043D\\U+043E\\U+043F\\U+043E\\U+043B\\U+044E\\U+0441\\U+043D\\U+044B\\U+0439" () (("\\U+041D\\U+041E\\U+041C.\\U+0422\\U+041E\\U+041A,\\U+0410" . "10") ("\\U+041E\\U+0422\\U+041A\\U+041B.\\U+0421\\U+041F\\U+041E\\U+0421\\U+041E\\U+0411\\U+041D\\U+041E\\U+0421\\U+0422\\U+042C,\\U+041A\\U+0410" . "6") ("\\U+0425\\U+0410\\U+0420\\U+0410\\U+041A\\U+0422\\U+0415\\U+0420\\U+0418\\U+0421\\U+0422\\U+0418\\U+041A\\U+0410" . "\\U+0421") ("\\U+041F\\U+0420\\U+041E\\U+0418\\U+0417\\U+0412\\U+041E\\U+0414\\U+0418\\U+0422\\U+0415\\U+041B\\U+042C" . "ABB") ("\\U+0421\\U+0415\\U+0420\\U+0418\\U+042F" . "S201\\U+0421") ("\\U+041D\\U+041E\\U+041C\\U+0415\\U+0420" . "")))
 )
 ("dev_a3"
  ("I" "\\U+0430\\U+043F\\U+043F\\U+0430\\U+0440\\U+0430\\U+0442 \\U+0443\\U+043F\\U+0440\\U+0430\\U+0432\\U+043B\\U+0435\\U+043D\\U+0438\\U+044F \\U+0438 \\U+0437\\U+0430\\U+0449\\U+0438\\U+0442\\U+044B \\U+0432 \\U+0420\\U+0429" 0.0 0.0 41.189524335 41.189524335 0.0 "\\U+0428\\U+0430\\U+043F\\U+043A\\U+0430 \\U+0449\\U+0438\\U+0442\\U+0430" nil nil "\\U+0410\\U+0432\\U+0442\\U+043E\\U+043C\\U+0430\\U+0442\\U+0438\\U+0447\\U+0435\\U+0441\\U+043A\\U+0438\\U+0439 \\U+0432\\U+044B\\U+043A\\U+043B\\U+044E\\U+0447\\U+0430\\U+0442\\U+0435\\U+043B\\U+044C \\U+0442\\U+0440\\U+0435\\U+0445\\U+043F\\U+043E\\U+043B\\U+044E\\U+0441\\U+043D\\U+044B\\U+0439" () (("\\U+041D\\U+041E\\U+041C.\\U+0422\\U+041E\\U+041A,\\U+0410" . "16") ("\\U+041E\\U+0422\\U+041A\\U+041B.\\U+0421\\U+041F\\U+041E\\U+0421\\U+041E\\U+0411\\U+041D\\U+041E\\U+0421\\U+0422\\U+042C,\\U+041A\\U+0410" . "6") ("\\U+0425\\U+0410\\U+0420\\U+0410\\U+041A\\U+0422\\U+0415\\U+0420\\U+0418\\U+0421\\U+0422\\U+0418\\U+041A\\U+0410" . "\\U+0421") ("\\U+041F\\U+0420\\U+041E\\U+0418\\U+0417\\U+0412\\U+041E\\U+0414\\U+0418\\U+0422\\U+0415\\U+041B\\U+042C" . "ABB") ("\\U+0421\\U+0415\\U+0420\\U+0418\\U+042F" . "S203\\U+0421") ("\\U+041D\\U+041E\\U+041C\\U+0415\\U+0420" . "")))
 )
 ("dev_d1"
  ("I" "\\U+0423\\U+0417\\U+041E \\U+0432 \\U+0420\\U+0429" 0.0 0.0 41.189524335 41.189524335 0.0 "0" nil nil "\\U+0410\\U+0432\\U+0442\\U+043E\\U+043C\\U+0430\\U+0442\\U+0438\\U+0447\\U+0435\\U+0441\\U+043A\\U+0438\\U+0439 \\U+0434\\U+0438\\U+0444\\U+0444\\U+0435\\U+0440\\U+0435\\U+043D\\U+0446\\U+0438\\U+0430\\U+043B\\U+044C\\U+043D\\U+044B\\U+0439 \\U+0432\\U+044B\\U+043A\\U+043B\\U+044E\\U+0447\\U+0430\\U+0442\\U+0435\\U+043B\\U+044C \\U+0434\\U+0432\\U+0443\\U+0445\\U+043F\\U+043E\\U+043B\\U+044E\\U+0441\\U+043D\\U+044B\\U+0439" () (("\\U+041D\\U+041E\\U+041C.\\U+0422\\U+041E\\U+041A,\\U+0410" . "16") ("\\U+041E\\U+0422\\U+041A\\U+041B.\\U+0421\\U+041F\\U+041E\\U+0421\\U+041E\\U+0411\\U+041D\\U+041E\\U+0421\\U+0422\\U+042C,\\U+041A\\U+0410" . "6") ("\\U+0425\\U+0410\\U+0420\\U+0410\\U+041A\\U+0422\\U+0415\\U+0420\\U+0418\\U+0421\\U+0422\\U+0418\\U+041A\\U+0410" . "\\U+0421") ("I\\U+0421\\U+0420.,\\U+041C\\U+0410" . "30") ("\\U+0422\\U+0418\\U+041F" . "\\U+0410C") ("\\U+041F\\U+0420\\U+041E\\U+0418\\U+0417\\U+0412\\U+041E\\U+0414\\U+0418\\U+0422\\U+0415\\U+041B\\U+042C" . "ABB") ("\\U+0421\\U+0415\\U+0420\\U+0418\\U+042F" . "DS201") ("\\U+041D\\U+041E\\U+041C\\U+0415\\U+0420" . "")))
 )
 ("dev_d3"
  ("I" "\\U+0423\\U+0417\\U+041E \\U+0432 \\U+0420\\U+0429" 0.0 0.0 41.189524335 41.189524335 0.0 "0" nil nil "\\U+0410\\U+0432\\U+0442\\U+043E\\U+043C\\U+0430\\U+0442\\U+0438\\U+0447\\U+0435\\U+0441\\U+043A\\U+0438\\U+0439 \\U+0434\\U+0438\\U+0444\\U+0444\\U+0435\\U+0440\\U+0435\\U+043D\\U+0446\\U+0438\\U+0430\\U+043B\\U+044C\\U+043D\\U+044B\\U+0439 \\U+0432\\U+044B\\U+043A\\U+043B\\U+044E\\U+0447\\U+0430\\U+0442\\U+0435\\U+043B\\U+044C \\U+0447\\U+0435\\U+0442\\U+044B\\U+0440\\U+0435\\U+0445\\U+043F\\U+043E\\U+043B\\U+044E\\U+0441\\U+043D\\U+044B\\U+0439" () (("\\U+041D\\U+041E\\U+041C.\\U+0422\\U+041E\\U+041A,\\U+0410" . "20") ("\\U+041E\\U+0422\\U+041A\\U+041B.\\U+0421\\U+041F\\U+041E\\U+0421\\U+041E\\U+0411\\U+041D\\U+041E\\U+0421\\U+0422\\U+042C,\\U+041A\\U+0410" . "6") ("\\U+0425\\U+0410\\U+0420\\U+0410\\U+041A\\U+0422\\U+0415\\U+0420\\U+0418\\U+0421\\U+0422\\U+0418\\U+041A\\U+0410" . "\\U+0421") ("I\\U+0421\\U+0420.,\\U+041C\\U+0410" . "30") ("\\U+0422\\U+0418\\U+041F" . "\\U+0410C") ("\\U+041F\\U+0420\\U+041E\\U+0418\\U+0417\\U+0412\\U+041E\\U+0414\\U+0418\\U+0422\\U+0415\\U+041B\\U+042C" . "ABB") ("\\U+0421\\U+0415\\U+0420\\U+0418\\U+042F" . "DS203NC") ("\\U+041D\\U+041E\\U+041C\\U+0415\\U+0420" . "")))
 )
 ("dot41"
  ("I" "A$C410E7F00" 0.0 0.0 41.189524335 41.189524335 0.0 "\\U+0428\\U+0430\\U+043F\\U+043A\\U+0430 \\U+0449\\U+0438\\U+0442\\U+0430" nil nil nil () ())
 )
 ("dot43"
  ("I" "A$C410E7F00" 0.0 0.0 43.357394036 43.357394036 0.0 "\\U+0428\\U+0430\\U+043F\\U+043A\\U+0430 \\U+0449\\U+0438\\U+0442\\U+0430" nil nil nil () ())
 )
 ("wire"
  ("E" . ((0 . "LINE") (100 . "AcDbEntity") (8 . "\\U+0428\\U+0430\\U+043F\\U+043A\\U+0430 \\U+0449\\U+0438\\U+0442\\U+0430") (370 . 0) (100 . "AcDbLine") (10 0.0 0.0 0.0) (11 -0.000000026 376.82829552 0.0)))
 )
 ("wire0"
  ("E" . ((0 . "LWPOLYLINE") (100 . "AcDbEntity") (8 . "0") (370 . 0) (100 . "AcDbPolyline") (90 . 2) (70 . 0) (43 . 0.0) (10 0.0 0.0) (10 0.000001122 -281.290652704)))
 )
 ("m_phase"
  ("E" . ((0 . "MTEXT") (100 . "AcDbEntity") (8 . "\\U+0428\\U+0430\\U+043F\\U+043A\\U+0430 \\U+0449\\U+0438\\U+0442\\U+0430") (370 . 0) (100 . "AcDbMText") (10 0.0 0.0 0.0) (40 . 100.0) (41 . 434.669033315) (46 . 0.0) (71 . 1) (72 . 5) (1 . "A") (7 . "ls_100") (73 . 1) (44 . 1.0)))
 )
 ("m_cable"
  ("E" . ((0 . "MTEXT") (100 . "AcDbEntity") (8 . "0") (370 . 0) (100 . "AcDbMText") (10 0.0 0.0 0.0) (40 . 102.973810837) (41 . 1088.417857763) (46 . 156.912473656) (71 . 1) (72 . 5) (1 . "{\\W0.6;\\U+0412\\U+0412\\U+0413\\U+043D\\U+0433LS 3x1,5}") (7 . "A_C") (11 0.0 1.0 0.0) (73 . 1) (44 . 1.0)))
 )
 ("m_cond"
  ("E" . ((0 . "MTEXT") (100 . "AcDbEntity") (8 . "0") (370 . 0) (100 . "AcDbMText") (10 0.0 0.0 0.0) (40 . 102.973810837) (41 . 823.790486693) (46 . 0.0) (71 . 1) (72 . 5) (1 . "\\U+041F16") (7 . "A_C") (11 0.0 1.0 0.0) (73 . 1) (44 . 1.0)))
 )
 ("m_name"
  ("E" . ((0 . "MTEXT") (100 . "AcDbEntity") (8 . "0") (370 . 0) (100 . "AcDbMText") (10 0.0 0.0 0.0) (40 . 120.0) (41 . 2493.87862559) (46 . 496.354736951) (71 . 1) (72 . 5) (1 . "\\pxsm1;{\\T0.9;\\U+041E\\U+0431\\U+0449\\U+0438\\U+0439 \\U+0432\\U+044B\\U+043A\\U+043B\\U+044E\\U+0447\\U+0430\\U+0442\\U+0435\\U+043B\\U+044C\\P\\U+043E\\U+0441\\U+0432\\U+0435\\U+0449\\U+0435\\U+043D\\U+0438\\U+044F}") (7 . "ls_100") (11 0.0 1.0 0.0) (73 . 1) (44 . 1.0)))
 )
 ("kup"
  ("E" . ((0 . "MTEXT") (100 . "AcDbEntity") (8 . "0") (370 . 0) (100 . "AcDbMText") (10 -187.395568323 -7030.184636033 0.0) (40 . 120.0) (41 . 2493.87862559) (46 . 496.37460955) (71 . 1) (72 . 5) (1 . "{\\T0.9;\\U+041A\\U+043E\\U+0440\\U+043E\\U+0431\\U+043A\\U+0438 \\U+0434\\U+043E\\U+043F\\U+043E\\U+043B\\U+043D\\U+0438\\U+0442\\U+0435\\U+043B\\U+044C\\U+043D\\U+043E\\U+0439 \\U+0441\\U+0438\\U+0441\\U+0442\\U+0435\\U+043C\\U+044B \\U+0443\\U+0440\\U+0430\\U+0432\\U+043D\\U+0438\\U+0432\\U+0430\\U+043D\\U+0438\\U+044F \\U+043F\\U+043E\\U+0442\\U+0435\\U+043D\\U+0446\\U+0438\\U+0430\\U+043B\\U+043E\\U+0432}") (7 . "ls_100") (11 0.0 1.0 0.0) (73 . 1) (44 . 1.0)))
  ("E" . ((0 . "MTEXT") (100 . "AcDbEntity") (8 . "0") (370 . 0) (100 . "AcDbMText") (10 -188.606013409 -4338.427103527 0.0) (40 . 108.38633212) (41 . 1480.810404913) (46 . 0.0) (71 . 1) (72 . 5) (1 . "{\\W0.6;\\U+041F\\U+0443\\U+0413\\U+0412\\U+043D\\U+0433(\\U+0410)-LS 1\\U+04456}") (7 . "A_C") (11 0.0 1.0 0.0) (73 . 1) (44 . 1.0)))
  ("E" . ((0 . "MTEXT") (100 . "AcDbEntity") (8 . "0") (370 . 0) (100 . "AcDbMText") (10 37.809033905 -4340.247886663 0.0) (40 . 108.38633212) (41 . 867.090656963) (46 . 0.0) (71 . 1) (72 . 5) (1 . "\\U+041F16 ") (7 . "A_C") (11 0.0 1.0 0.0) (73 . 1) (44 . 1.0)))
  ("E" . ((0 . "TEXT") (100 . "AcDbEntity") (8 . "2\\U+04451.5") (370 . 0) (100 . "AcDbText") (10 -95.658173274 -4467.59265851 0.0) (40 . 75.0) (1 . "\\U+041A\\U+0423\\U+041F") (7 . "Is_150") (100 . "AcDbText")))
  ("E" . ((0 . "LWPOLYLINE") (100 . "AcDbEntity") (8 . "2\\U+04451.5") (370 . 0) (100 . "AcDbPolyline") (90 . 4) (70 . 1) (43 . 6.666666667) (10 -117.305049743 -4360.509549431) (10 116.594950257 -4360.509549431) (10 116.594950257 -4510.255909973) (10 -117.305049743 -4510.255909973)))
 )
 ("mont"
  ("E" . ((0 . "MTEXT") (100 . "AcDbEntity") (8 . "TEXT") (6 . "Continuous") (62 . 0) (370 . 0) (100 . "AcDbMText") (10 -6250.000230069 625.000000001 0.0) (40 . 150.0) (41 . 3500.00023007) (46 . 750.0) (71 . 4) (72 . 5) (1 . "\\pxqc;\\U+041A\\U+043E\\U+043C\\U+043F\\U+043E\\U+043D\\U+043E\\U+0432\\U+043A\\U+0430 \\U+0449\\U+0438\\U+0442\\U+0430") (7 . "ls_200") (73 . 2) (44 . 1.0)))
  ("E" . ((0 . "MTEXT") (100 . "AcDbEntity") (8 . "TEXT") (6 . "Continuous") (62 . 0) (370 . 0) (100 . "AcDbMText") (10 -2750.000230069 1250.000000001 0.0) (40 . 150.0) (41 . 750.00023007) (46 . 500.0) (71 . 4) (72 . 5) (1 . "\\pxqc;\\U+0420") (7 . "ls_200") (73 . 2) (44 . 1.0)))
  ("E" . ((0 . "MTEXT") (100 . "AcDbEntity") (8 . "TEXT") (6 . "Continuous") (62 . 0) (370 . 0) (100 . "AcDbMText") (10 -2000.000230069 1250.000000001 0.0) (40 . 150.0) (41 . 850.00023007) (46 . 500.0) (71 . 4) (72 . 5) (1 . "\\pxqc;10") (7 . "ls_200") (73 . 2) (44 . 1.0)))
  ("I" "\\U+04103-GIP-ALBOM" 0.0 0.0 1.0 1.0 0.0 "FORMAT" nil nil "\\U+042D\\U+041E\\U+041C" () ())
  ("E" . ((0 . "TEXT") (100 . "AcDbEntity") (8 . "Ramka") (370 . 0) (100 . "AcDbText") (10 -11421.500000001 14200.224150419 0.0) (40 . 225.0) (1 . "\\U+041A\\U+043E\\U+043C\\U+043F\\U+043E\\U+043D\\U+043E\\U+0432\\U+043A\\U+0430 \\U+0449\\U+0438\\U+0442\\U+0430") (7 . "ls_200") (72 . 1) (11 -10105.250000001 14312.724150419 0.0) (100 . "AcDbText") (73 . 2)))
 )
 ("c_roz"
  ("I" "\\U+042D\\U+041E\\U+041C_\\U+0420\\U+043E\\U+0437\\U+0435\\U+0442\\U+043A\\U+0438_GIP" 0.0 0.0 1.0 1.0 180.0 "\\U+0440\\U+043E\\U+0437\\U+0435\\U+0442\\U+043A\\U+0438 \\U+0441\\U+0438\\U+043B\\U+043E\\U+0432\\U+044B\\U+0435" nil 3.0 "\\U+0420\\U+043E\\U+0437\\U+0435\\U+0442\\U+043A\\U+0430 \\U+0448\\U+0442\\U+0435\\U+043F\\U+0441\\U+0435\\U+043B\\U+044C\\U+043D\\U+0430\\U+044F \\U+0441\\U+0438\\U+043B\\U+043E\\U+0432\\U+0430\\U+044F, 16A, L+N+PE (1\\U+0424)" (("\\U+041F\\U+043E\\U+043B\\U+043E\\U+0436\\U+0435\\U+043D\\U+0438\\U+04354 Y" . 70.0) ("\\U+0421\\U+0442\\U+0435\\U+043F\\U+0435\\U+043D\\U+044C \\U+0437\\U+0430\\U+0449\\U+0438\\U+0442\\U+044B" . "IP20")) (("\\U+041F\\U+041E\\U+0417\\U+0418\\U+0426\\U+0418\\U+042F" . "") ("\\U+0418\\U+041C\\U+042F" . "\\U+0420\\U+043E\\U+0437\\U+0435\\U+0442\\U+043A\\U+0430 \\U+0448\\U+0442\\U+0435\\U+043F\\U+0441\\U+0435\\U+043B\\U+044C\\U+043D\\U+0430\\U+044F \\U+0441\\U+0438\\U+043B\\U+043E\\U+0432\\U+0430\\U+044F, 16A, L+N+PE (1\\U+0424)") ("\\U+0422\\U+0418\\U+041F" . "") ("\\U+0420\\U+0410\\U+0417\\U+041C\\U+0415\\U+0420" . "") ("\\U+0410\\U+0420\\U+0422\\U+0418\\U+041A\\U+0423\\U+041B" . "") ("\\U+041F\\U+0420\\U+041E\\U+0418\\U+0417\\U+0412\\U+041E\\U+0414\\U+0418\\U+0422\\U+0415\\U+041B\\U+042C" . "") ("\\U+041C\\U+0410\\U+0421\\U+0421\\U+0410" . "") ("\\U+041F\\U+0420\\U+0418\\U+041C\\U+0415\\U+0427\\U+0410\\U+041D\\U+0418\\U+0415" . "")))
 )
 ("c_roz44"
  ("I" "\\U+042D\\U+041E\\U+041C_\\U+0420\\U+043E\\U+0437\\U+0435\\U+0442\\U+043A\\U+0438_GIP" 0.0 0.0 1.0 1.0 180.0 "\\U+0440\\U+043E\\U+0437\\U+0435\\U+0442\\U+043A\\U+0438 \\U+0441\\U+0438\\U+043B\\U+043E\\U+0432\\U+044B\\U+0435" nil 3.0 "\\U+0420\\U+043E\\U+0437\\U+0435\\U+0442\\U+043A\\U+0430 \\U+0448\\U+0442\\U+0435\\U+043F\\U+0441\\U+0435\\U+043B\\U+044C\\U+043D\\U+0430\\U+044F \\U+0441\\U+0438\\U+043B\\U+043E\\U+0432\\U+0430\\U+044F, 16A, L+N+PE (1\\U+0424) IP44" (("\\U+041F\\U+043E\\U+043B\\U+043E\\U+0436\\U+0435\\U+043D\\U+0438\\U+04354 Y" . 70.0) ("\\U+0421\\U+0442\\U+0435\\U+043F\\U+0435\\U+043D\\U+044C \\U+0437\\U+0430\\U+0449\\U+0438\\U+0442\\U+044B" . "IP44") ("Block Table1" . 2)) (("\\U+041F\\U+041E\\U+0417\\U+0418\\U+0426\\U+0418\\U+042F" . "") ("\\U+0418\\U+041C\\U+042F" . "\\U+0420\\U+043E\\U+0437\\U+0435\\U+0442\\U+043A\\U+0430 \\U+0448\\U+0442\\U+0435\\U+043F\\U+0441\\U+0435\\U+043B\\U+044C\\U+043D\\U+0430\\U+044F \\U+0441\\U+0438\\U+043B\\U+043E\\U+0432\\U+0430\\U+044F, 16A, L+N+PE (1\\U+0424) IP44") ("\\U+0422\\U+0418\\U+041F" . "") ("\\U+0420\\U+0410\\U+0417\\U+041C\\U+0415\\U+0420" . "") ("\\U+0410\\U+0420\\U+0422\\U+0418\\U+041A\\U+0423\\U+041B" . "") ("\\U+041F\\U+0420\\U+041E\\U+0418\\U+0417\\U+0412\\U+041E\\U+0414\\U+0418\\U+0422\\U+0415\\U+041B\\U+042C" . "") ("\\U+041C\\U+0410\\U+0421\\U+0421\\U+0410" . "") ("\\U+041F\\U+0420\\U+0418\\U+041C\\U+0415\\U+0427\\U+0410\\U+041D\\U+0418\\U+0415" . "")))
 )
 ("c_tp"
  ("I" "\\U+042D\\U+041E\\U+041C_\\U+0420\\U+043E\\U+0437\\U+0435\\U+0442\\U+043A\\U+0438_GIP" 0.0 0.0 1.0 1.0 359.874685229 "\\U+0440\\U+043E\\U+0437\\U+0435\\U+0442\\U+043A\\U+0438 \\U+0441\\U+0438\\U+043B\\U+043E\\U+0432\\U+044B\\U+0435" nil 3.0 "\\U+0422\\U+0435\\U+0440\\U+043C\\U+043E\\U+0440\\U+0435\\U+0433\\U+0443\\U+043B\\U+044F\\U+0442\\U+043E\\U+0440 \\U+0422\\U+041F" (("\\U+041F\\U+043E\\U+043B\\U+043E\\U+0436\\U+0435\\U+043D\\U+0438\\U+04354 Y" . 70.0)) (("\\U+041F\\U+041E\\U+0417\\U+0418\\U+0426\\U+0418\\U+042F" . "") ("\\U+0418\\U+041C\\U+042F" . "\\U+0422\\U+0435\\U+0440\\U+043C\\U+043E\\U+0440\\U+0435\\U+0433\\U+0443\\U+043B\\U+044F\\U+0442\\U+043E\\U+0440 \\U+0422\\U+041F") ("\\U+0422\\U+0418\\U+041F" . "") ("\\U+0420\\U+0410\\U+0417\\U+041C\\U+0415\\U+0420" . "") ("\\U+0410\\U+0420\\U+0422\\U+0418\\U+041A\\U+0423\\U+041B" . "") ("\\U+041F\\U+0420\\U+041E\\U+0418\\U+0417\\U+0412\\U+041E\\U+0414\\U+0418\\U+0422\\U+0415\\U+041B\\U+042C" . "") ("\\U+041C\\U+0410\\U+0421\\U+0421\\U+0410" . "") ("\\U+041F\\U+0420\\U+0418\\U+041C\\U+0415\\U+0427\\U+0410\\U+041D\\U+0418\\U+0415" . "")))
 )
 ("c_kab"
  ("I" "\\U+0432\\U+044B\\U+0432\\U+043E\\U+0434 \\U+043A\\U+0430\\U+0431\\U+0435\\U+043B\\U+044F" 0.0 0.0 39.541943361 39.541943361 0.0 "3\\U+04452.5" nil nil "\\U+0441 \\U+043A\\U+0440\\U+0443\\U+0436\\U+0435\\U+0447\\U+043A\\U+043E\\U+043C" (("Angle" . 4.71238898)) ())
 )
 ("c_svet"
  ("I" "\\U+0442\\U+043E\\U+0447\\U+0435\\U+0447\\U+043D\\U+044B\\U+0439 \\U+0441 \\U+043B\\U+0430\\U+043C\\U+043F\\U+043E\\U+0439 \\U+043D\\U+0430\\U+043A\\U+0430\\U+043B\\U+0438\\U+0432\\U+0430\\U+043D\\U+0438\\U+044F" 0.0 0.0 51.486905418 51.486905418 0.0 "\\U+0441\\U+0432\\U+0435\\U+0442\\U+0438\\U+043B\\U+044C\\U+043D\\U+0438\\U+043A\\U+0438" nil nil nil () (("\\U+0422\\U+0418\\U+041F" . "R63W")))
 )
 ("specpage"
  ("E" . ((0 . "LWPOLYLINE") (100 . "AcDbEntity") (8 . "FORMAT") (100 . "AcDbPolyline") (90 . 4) (70 . 1) (43 . 0.0) (10 -20960.500000001 14850.0) (10 0.0 14850.0) (10 0.0 29700.0) (10 -20960.500000001 29700.0)))
  ("E" . ((0 . "MTEXT") (100 . "AcDbEntity") (8 . "TEXT") (6 . "Continuous") (62 . 0) (370 . 0) (100 . "AcDbMText") (10 -6250.000230069 625.000000001 0.0) (40 . 150.0) (41 . 3500.00023007) (46 . 750.0) (71 . 4) (72 . 5) (1 . "\\pxqc;\\U+0421\\U+043F\\U+0435\\U+0446\\U+0438\\U+0444\\U+0438\\U+043A\\U+0430\\U+0446\\U+0438\\U+044F \\U+044D\\U+043B\\U+0435\\U+043A\\U+0442\\U+0440\\U+043E\\U+043E\\U+0431\\U+043E\\U+0440\\U+0443\\U+0434\\U+043E\\U+0432\\U+0430\\U+043D\\U+0438\\U+044F \\P\\U+0438 \\U+044D\\U+043B\\U+0435\\U+043A\\U+0442\\U+0440\\U+043E\\U+043E\\U+0441\\U+0432\\U+0435\\U+0449\\U+0435\\U+043D\\U+0438\\U+044F") (7 . "ls_200") (73 . 2) (44 . 1.0)))
  ("E" . ((0 . "MTEXT") (100 . "AcDbEntity") (8 . "TEXT") (6 . "Continuous") (62 . 0) (370 . 0) (100 . "AcDbMText") (10 -2750.000230069 1250.000000001 0.0) (40 . 150.0) (41 . 750.00023007) (46 . 500.0) (71 . 4) (72 . 5) (1 . "\\pxqc;\\U+0420") (7 . "ls_200") (73 . 2) (44 . 1.0)))
  ("E" . ((0 . "MTEXT") (100 . "AcDbEntity") (8 . "TEXT") (6 . "Continuous") (62 . 0) (370 . 0) (100 . "AcDbMText") (10 -2000.000230069 1250.000000001 0.0) (40 . 150.0) (41 . 850.00023007) (46 . 500.0) (71 . 4) (72 . 5) (1 . "\\pxqc;1") (7 . "ls_200") (73 . 2) (44 . 1.0)))
  ("E" . ((0 . "MTEXT") (100 . "AcDbEntity") (8 . "TEXT") (6 . "Continuous") (62 . 0) (370 . 0) (100 . "AcDbMText") (10 -1150.000230069 1250.000000001 0.0) (40 . 150.0) (41 . 900.000230069) (46 . 500.0) (71 . 4) (72 . 5) (1 . "\\pxqc;2") (7 . "ls_200") (73 . 2) (44 . 1.0)))
  ("E" . ((0 . "LWPOLYLINE") (100 . "AcDbEntity") (8 . "FORMAT") (100 . "AcDbPolyline") (90 . 4) (70 . 1) (43 . 0.0) (10 -20960.500000001 0.0) (10 0.0 0.0) (10 0.0 14850.0) (10 -20960.500000001 14850.0)))
  ("E" . ((0 . "MTEXT") (100 . "AcDbEntity") (8 . "TEXT") (6 . "Continuous") (62 . 0) (370 . 0) (100 . "AcDbMText") (10 -14730.25 500.000000001 0.0) (40 . 150.0) (41 . 10460.500000002) (46 . 500.000000001) (71 . 5) (72 . 5) (1 . "\\pxl1,sm0.7,ql;\t\\U+0425\\U+0430\\U+0440\\U+0430\\U+043A\\U+0442\\U+0435\\U+0440\\U+0438\\U+0441\\U+0442\\U+0438\\U+043A\\U+0438 \\U+043E\\U+0431\\U+043E\\U+0440\\U+0443\\U+0434\\U+043E\\U+0432\\U+0430\\U+043D\\U+0438\\U+044F \\U+0438 \\U+043C\\U+0430\\U+0442\\U+0435\\U+0440\\U+0430\\U+043B\\U+043E\\U+0432 \\U+043E\\U+043F\\U+0440\\U+0435\\U+0434\\U+0435\\U+043B\\U+044F\\U+044E\\U+0442\\U+0441\\U+044F \\U+043F\\U+0440\\U+043E\\U+0435\\U+043A\\U+0442\\U+043E\\U+043C, \\U+043E\\U+043A\\U+043E\\U+043D\\U+0447\\U+0430\\U+0442\\U+0435\\U+043B\\U+044C\\U+043D\\U+044B\\U+0439 \\P\\U+0432\\U+044B\\U+0431\\U+043E\\U+0440 \\U+043C\\U+0430\\U+0440\\U+043E\\U+043A \\U+0438 \\U+043C\\U+043E\\U+0434\\U+0435\\U+043B\\U+0435\\U+0439 \\U+043E\\U+0431\\U+043E\\U+0440\\U+0443\\U+0434\\U+043E\\U+0432\\U+0430\\U+043D\\U+0438\\U+044F \\U+0438 \\U+043C\\U+0430\\U+0442\\U+0435\\U+0440\\U+0438\\U+0430\\U+043B\\U+043E\\U+0432 \\U+043F\\U+0440\\U+043E\\U+0438\\U+0437\\U+0432\\U+043E\\U+0434\\U+0438\\U+0442 \\U+0437\\U+0430\\U+043A\\U+0430\\U+0437\\U+0447\\U+0438\\U+043A.") (7 . "ls_200") (73 . 2) (44 . 1.0)))
  ("E" . ((0 . "LINE") (100 . "AcDbEntity") (8 . "0") (62 . 7) (370 . 9) (100 . "AcDbLine") (10 -19960.500000001 13800.0 0.0) (11 -250.0 13800.000000001 0.0)))
  ("E" . ((0 . "LINE") (100 . "AcDbEntity") (8 . "0") (370 . 9) (100 . "AcDbLine") (10 -18960.500000001 13800.0 0.0) (11 -18960.500000001 14600.0 0.0)))
  ("E" . ((0 . "LINE") (100 . "AcDbEntity") (8 . "0") (370 . 9) (100 . "AcDbLine") (10 -10960.500000001 13800.0 0.0) (11 -10960.500000001 14600.0 0.0)))
  ("E" . ((0 . "LINE") (100 . "AcDbEntity") (8 . "0") (370 . 9) (100 . "AcDbLine") (10 -8560.500000001 13800.0 0.0) (11 -8560.500000001 14600.0 0.0)))
  ("E" . ((0 . "LINE") (100 . "AcDbEntity") (8 . "0") (370 . 9) (100 . "AcDbLine") (10 -6710.500000001 13800.0 0.0) (11 -6710.500000001 14600.0 0.0)))
  ("E" . ((0 . "LINE") (100 . "AcDbEntity") (8 . "0") (370 . 9) (100 . "AcDbLine") (10 -4760.500000001 13800.0 0.0) (11 -4760.500000001 14600.0 0.0)))
  ("E" . ((0 . "LINE") (100 . "AcDbEntity") (8 . "0") (370 . 9) (100 . "AcDbLine") (10 -3660.500000001 13800.0 0.0) (11 -3660.500000001 14600.0 0.0)))
  ("E" . ((0 . "LINE") (100 . "AcDbEntity") (8 . "0") (370 . 9) (100 . "AcDbLine") (10 -2460.500000001 13800.0 0.0) (11 -2460.500000001 14599.999999998 0.0)))
  ("E" . ((0 . "MTEXT") (100 . "AcDbEntity") (8 . "TEXT") (6 . "Continuous") (62 . 0) (370 . 0) (100 . "AcDbMText") (10 -19460.500000001 14200.0 0.0) (40 . 150.0) (41 . 1000.0) (46 . 800.0) (71 . 5) (72 . 5) (1 . "\\pxqc;\\U+041F\\U+043E\\U+0437\\U+0438\\U+0446\\U+0438\\U+044F") (7 . "ls_200") (73 . 2) (44 . 1.0)))
  ("E" . ((0 . "MTEXT") (100 . "AcDbEntity") (8 . "TEXT") (6 . "Continuous") (62 . 0) (370 . 0) (100 . "AcDbMText") (10 -14960.500000001 14200.0 0.0) (40 . 150.0) (41 . 8000.0) (46 . 800.0) (71 . 5) (72 . 5) (1 . "\\pxqc;\\U+041D\\U+0430\\U+0438\\U+043C\\U+0435\\U+043D\\U+043E\\U+0432\\U+0430\\U+043D\\U+0438\\U+0435 \\U+0438 \\U+0442\\U+0435\\U+0445\\U+043D\\U+0438\\U+0447\\U+0435\\U+0441\\U+043A\\U+0430\\U+044F \\U+0445\\U+0430\\U+0440\\U+0430\\U+043A\\U+0442\\U+0435\\U+0440\\U+0438\\U+0441\\U+0442\\U+0438\\U+043A\\U+0430") (7 . "ls_200") (73 . 2) (44 . 1.0)))
  ("E" . ((0 . "MTEXT") (100 . "AcDbEntity") (8 . "TEXT") (6 . "Continuous") (62 . 0) (370 . 0) (100 . "AcDbMText") (10 -9760.500000001 14200.0 0.0) (40 . 150.0) (41 . 2400.0) (46 . 800.0) (71 . 5) (72 . 5) (1 . "\\pxqc;\\U+0422\\U+0438\\U+043F, \\U+043C\\U+0430\\U+0440\\U+043A\\U+0430,\\P\\U+043E\\U+0431\\U+043E\\U+0437\\U+043D\\U+0430\\U+0447\\U+0435\\U+043D\\U+0438\\U+0435 \\U+0434\\U+043E\\U+043A\\U+0443\\U+043C\\U+0435\\U+043D\\U+0442\\U+0430,\\P\\U+043E\\U+043F\\U+0440\\U+043E\\U+0441\\U+043D\\U+043E\\U+0433\\U+043E \\U+043B\\U+0438\\U+0441\\U+0442\\U+0430") (7 . "ls_200") (73 . 2) (44 . 1.0)))
  ("E" . ((0 . "MTEXT") (100 . "AcDbEntity") (8 . "TEXT") (6 . "Continuous") (62 . 0) (370 . 0) (100 . "AcDbMText") (10 -7635.500000001 14200.0 0.0) (40 . 150.0) (41 . 1850.0) (46 . 800.0) (71 . 5) (72 . 5) (1 . "\\pxqc;\\U+041A\\U+043E\\U+0434 \\U+043E\\U+0431\\U+043E\\U+0440\\U+0443\\U+0434\\U+043E\\U+0432\\U+0430\\U+043D\\U+0438\\U+044F,\\P\\U+0438\\U+0437\\U+0434\\U+0435\\U+043B\\U+0438\\U+044F,\\P\\U+043C\\U+0430\\U+0442\\U+0435\\U+0440\\U+0438\\U+0430\\U+043B\\U+0430") (7 . "ls_200") (73 . 2) (44 . 1.0)))
  ("E" . ((0 . "MTEXT") (100 . "AcDbEntity") (8 . "TEXT") (6 . "Continuous") (62 . 0) (370 . 0) (100 . "AcDbMText") (10 -5735.500000001 14200.0 0.0) (40 . 150.0) (41 . 1950.0) (46 . 800.0) (71 . 5) (72 . 5) (1 . "\\pxqc;\\U+0417\\U+0430\\U+0432\\U+043E\\U+0434 -\\P\\U+0438\\U+0437\\U+0433\\U+043E\\U+0442\\U+043E\\U+0432\\U+0438\\U+0442\\U+0435\\U+043B\\U+044C") (7 . "ls_200") (73 . 2) (44 . 1.0)))
  ("E" . ((0 . "MTEXT") (100 . "AcDbEntity") (8 . "TEXT") (6 . "Continuous") (62 . 0) (370 . 0) (100 . "AcDbMText") (10 -4210.500000001 14200.0 0.0) (40 . 150.0) (41 . 1100.0) (46 . 800.0) (71 . 5) (72 . 5) (1 . "\\pxqc;\\U+0415\\U+0434\\U+0438\\U+043D\\U+0438\\U+0446\\U+0430\\P\\U+0438\\U+0437\\U+043C\\U+0435\\U+0440\\U+0435\\U+043D\\U+0438\\U+044F") (7 . "ls_200") (73 . 2) (44 . 1.0)))
  ("E" . ((0 . "MTEXT") (100 . "AcDbEntity") (8 . "TEXT") (6 . "Continuous") (62 . 0) (370 . 0) (100 . "AcDbMText") (10 -2010.500000001 14200.0 0.0) (40 . 150.0) (41 . 900.0) (46 . 800.0) (71 . 5) (72 . 5) (1 . "\\pxqc;\\U+041C\\U+0430\\U+0441\\U+0441\\U+0430 \\U+0435\\U+0434\\U+0438\\U+043D\\U+0438\\U+0446\\U+044B (\\U+043A\\U+0433)") (7 . "ls_200") (73 . 2) (44 . 1.0)))
  ("E" . ((0 . "MTEXT") (100 . "AcDbEntity") (8 . "TEXT") (6 . "Continuous") (62 . 0) (370 . 0) (100 . "AcDbMText") (10 -905.250000001 14200.0 0.0) (40 . 150.0) (41 . 1310.500000001) (46 . 800.0) (71 . 5) (72 . 5) (1 . "\\pxqc;\\U+041F\\U+0440\\U+0438\\U+043C\\U+0435\\U+0447\\U+0430\\U+043D\\U+0438\\U+0435") (7 . "ls_200") (73 . 2) (44 . 1.0)))
  ("E" . ((0 . "MTEXT") (100 . "AcDbEntity") (8 . "TEXT") (6 . "Continuous") (62 . 0) (370 . 0) (100 . "AcDbMText") (10 -3060.500000001 14200.001819443 0.0) (40 . 150.0) (41 . 1200.0) (46 . 800.0) (71 . 5) (72 . 5) (1 . "\\pxqc;\\U+041A\\U+043E\\U+043B\\U+0438\\U+0447\\U+0435\\U+0441\\U+0442\\U+0432\\U+043E") (7 . "ls_200") (73 . 2) (44 . 1.0)))
  ("E" . ((0 . "LINE") (100 . "AcDbEntity") (8 . "0") (370 . 9) (100 . "AcDbLine") (10 -1560.500000001 13799.998180549 0.0) (11 -1560.500000001 14599.998180549 0.0)))
 )
 ("cell_secname"
  ("E" . ((0 . "MTEXT") (100 . "AcDbEntity") (8 . "TEXT") (6 . "Continuous") (62 . 0) (370 . 0) (100 . "AcDbMText") (10 0.0 0.0 0.0) (40 . 150.0) (41 . 8000.0) (46 . 400.0) (71 . 5) (72 . 5) (1 . "\\pxi1,qc;\\U+0429\\U+0438\\U+0442\\U+043E\\U+0432\\U+043E\\U+0435 \\U+043E\\U+0431\\U+043E\\U+0440\\U+0443\\U+0434\\U+043E\\U+0432\\U+0430\\U+043D\\U+0438\\U+0435") (7 . "ls_200") (73 . 2) (44 . 1.0)))
 )
 ("cell_secpos"
  ("E" . ((0 . "MTEXT") (100 . "AcDbEntity") (8 . "TEXT") (6 . "Continuous") (62 . 0) (370 . 0) (100 . "AcDbMText") (10 0.0 0.0 0.0) (40 . 150.0) (41 . 1000.0) (46 . 400.0) (71 . 5) (72 . 5) (1 . "\\pxqc;1") (7 . "ls_200") (73 . 2) (44 . 1.0)))
 )
 ("cell_unit"
  ("E" . ((0 . "MTEXT") (100 . "AcDbEntity") (8 . "TEXT") (6 . "Continuous") (62 . 0) (370 . 0) (100 . "AcDbMText") (10 0.0 0.0 0.0) (40 . 150.0) (41 . 1100.0) (46 . 400.0) (71 . 5) (72 . 5) (1 . "\\pxsm0.75,qc;{\\C256;\\U+0448\\U+0442.}") (7 . "ls_200") (73 . 2) (44 . 1.0)))
 )
 ("cell_qty"
  ("E" . ((0 . "MTEXT") (100 . "AcDbEntity") (8 . "TEXT") (6 . "Continuous") (62 . 0) (370 . 0) (100 . "AcDbMText") (10 0.0 0.0 0.0) (40 . 150.0) (41 . 1200.0) (46 . 400.0) (71 . 5) (72 . 5) (1 . "\\pxsm0.75,qc;{\\C256;1}") (7 . "ls_200") (73 . 2) (44 . 1.0)))
 )
 ("cell_name"
  ("E" . ((0 . "MTEXT") (100 . "AcDbEntity") (8 . "TEXT") (6 . "Continuous") (62 . 0) (370 . 0) (100 . "AcDbMText") (10 0.0 0.0 0.0) (40 . 150.0) (41 . 8000.0) (46 . 400.0) (71 . 5) (72 . 5) (1 . "\\pxl1,sm0.7,ql;\\U+0429\\U+0438\\U+0442 \\U+0440\\U+0430\\U+0441\\U+043F\\U+0440\\U+0435\\U+0434\\U+0435\\U+043B\\U+0438\\U+0442\\U+0435\\U+043B\\U+044C\\U+043D\\U+044B\\U+0439 \\U+0432\\U+0441\\U+0442\\U+0440\\U+0430\\U+0438\\U+0432\\U+0430\\U+0435\\U+043C\\U+044B\\U+0439 \\U+0441 \\U+043A\\U+043B\\U+0435\\U+043C\\U+043C\\U+043D\\U+0438\\U+043A\\U+0430\\U+043C\\U+0438 N/PE, IP 40, 36 \\U+043C\\U+043E\\U+0434.") (7 . "ls_200") (73 . 2) (44 . 1.0)))
 )
 ("cell_maker"
  ("E" . ((0 . "MTEXT") (100 . "AcDbEntity") (8 . "TEXT") (6 . "Continuous") (62 . 0) (370 . 0) (100 . "AcDbMText") (10 0.0 0.0 0.0) (40 . 150.0) (41 . 1950.0) (46 . 400.0) (71 . 5) (72 . 5) (1 . "\\pxqc;{\\C256;ABB}") (7 . "ls_200") (73 . 2) (44 . 1.0)))
 )
 ("cell_type"
  ("E" . ((0 . "MTEXT") (100 . "AcDbEntity") (8 . "TEXT") (6 . "Continuous") (62 . 0) (370 . 0) (100 . "AcDbMText") (10 0.0 0.0 0.0) (40 . 150.0) (41 . 2400.0) (46 . 400.0) (71 . 5) (72 . 5) (1 . "\\pxqc;{\\C256;S202C}") (7 . "ls_200") (73 . 2) (44 . 1.0)))
 )
 ("cell_type7"
  ("E" . ((0 . "MTEXT") (100 . "AcDbEntity") (8 . "TEXT") (6 . "Continuous") (62 . 0) (370 . 0) (100 . "AcDbMText") (10 0.0 0.0 0.0) (40 . 150.0) (41 . 2400.0) (46 . 400.0) (71 . 5) (72 . 5) (1 . "\\pxsm0.7,qc;{\\C256;\\U+043E\\U+043F\\U+0440\\U+0435\\U+0434\\U+0435\\U+043B\\U+044F\\U+0435\\U+0442\\U+0441\\U+044F \\U+0437\\U+0430\\U+043A\\U+0430\\U+0437\\U+0447\\U+0438\\U+043A\\U+043E\\U+043C}") (7 . "ls_200") (73 . 2) (44 . 1.0)))
 )
 ("specrow"
  ("E" . ((0 . "LINE") (100 . "AcDbEntity") (8 . "0") (370 . 9) (100 . "AcDbLine") (10 -18960.500000001 -200.0 0.0) (11 -18960.500000001 200.0 0.0)))
  ("E" . ((0 . "LINE") (100 . "AcDbEntity") (8 . "0") (370 . 9) (100 . "AcDbLine") (10 -10960.500000001 -200.0 0.0) (11 -10960.500000001 200.0 0.0)))
  ("E" . ((0 . "LINE") (100 . "AcDbEntity") (8 . "0") (370 . 9) (100 . "AcDbLine") (10 -8560.500000001 -200.0 0.0) (11 -8560.500000001 200.0 0.0)))
  ("E" . ((0 . "LINE") (100 . "AcDbEntity") (8 . "0") (370 . 9) (100 . "AcDbLine") (10 -6710.500000001 -200.0 0.0) (11 -6710.500000001 200.0 0.0)))
  ("E" . ((0 . "LINE") (100 . "AcDbEntity") (8 . "0") (370 . 9) (100 . "AcDbLine") (10 -4760.500000001 -200.0 0.0) (11 -4760.500000001 200.0 0.0)))
  ("E" . ((0 . "LINE") (100 . "AcDbEntity") (8 . "0") (370 . 9) (100 . "AcDbLine") (10 -3660.500000001 -200.0 0.0) (11 -3660.500000001 200.0 0.0)))
  ("E" . ((0 . "LINE") (100 . "AcDbEntity") (8 . "0") (370 . 9) (100 . "AcDbLine") (10 -2460.500000001 -200.0 0.0) (11 -2460.500000001 200.0 0.0)))
  ("E" . ((0 . "LINE") (100 . "AcDbEntity") (8 . "0") (370 . 9) (100 . "AcDbLine") (10 -1560.500000001 -200.0 0.0) (11 -1560.500000001 200.0 0.0)))
  ("E" . ((0 . "LINE") (100 . "AcDbEntity") (8 . "0") (62 . 7) (370 . 9) (100 . "AcDbLine") (10 -19960.500000001 -200.0 0.0) (11 -250.0 -200.0 0.0)))
 )
)))
;;; шаблоны надписей номинала в блоках GIPM_*
(setq *gip:mtpl* (gip:deep-u (quote (
("GIPM_dk_a1" ("\\U+041D\\U+041E\\U+041C\\U+0418\\U+041D\\U+0410\\U+041B" . "{R} 230/400\\U+0412 ~"))
("GIPM_dk_a2" ("\\U+041D\\U+041E\\U+041C\\U+0418\\U+041D\\U+0410\\U+041B" . "{R} 230/400\\U+0412 ~"))
("GIPM_dk_a3" ("\\U+041D\\U+041E\\U+041C\\U+0418\\U+041D\\U+0410\\U+041B" . "{R} 230/400\\U+0412 ~"))
("GIPM_dk_a4" ("\\U+041D\\U+041E\\U+041C\\U+0418\\U+041D\\U+0410\\U+041B" . "{R} 230/400\\U+0412 ~"))
("GIPM_dk_dif" ("\\U+041D\\U+041E\\U+041C\\U+0418\\U+041D\\U+0410\\U+041B" . "{R}") ("\\U+0422\\U+041E\\U+041A\\U+0423\\U+0422\\U+0415\\U+0427\\U+041A\\U+0418" . "{M} ( I\\U+2206n)"))
("GIPM_dk_dif4" ("\\U+041D\\U+041E\\U+041C\\U+0418\\U+041D\\U+0410\\U+041B" . "{R}") ("\\U+0422\\U+041E\\U+041A\\U+0423\\U+0422\\U+0415\\U+0427\\U+041A\\U+0418" . "{M} ( I\\U+2206n)"))
("GIPM_dk_rcd2" ("\\U+041D\\U+041E\\U+041C\\U+0418\\U+041D\\U+0410\\U+041B" . "{R}") ("\\U+0422\\U+041E\\U+041A\\U+0423\\U+0422\\U+0415\\U+0427\\U+041A\\U+0418" . "{M} ( I\\U+2206n) 230\\U+0412 ~ Im: 500A t<0.1c"))
("GIPM_dk_rcd4" ("\\U+041D\\U+041E\\U+041C\\U+0418\\U+041D\\U+0410\\U+041B" . "{R}") ("\\U+0422\\U+041E\\U+041A\\U+0423\\U+0422\\U+0415\\U+0427\\U+041A\\U+0418" . "{M} ( I\\U+2206n) 415 \\U+0412 ~ Im: 500A t<0.1c"))
("GIPM_abb_km2" )
("GIPM_abb_km4" )
("GIPM_ab_a1" ("\\U+041D\\U+041E\\U+041C\\U+0418\\U+041D\\U+0410\\U+041B" . "{R}"))
("GIPM_ab_a2" ("\\U+041D\\U+041E\\U+041C\\U+0418\\U+041D\\U+0410\\U+041B" . "{R}"))
("GIPM_ab_a3" ("\\U+041D\\U+041E\\U+041C\\U+0418\\U+041D\\U+0410\\U+041B" . "{R}"))
("GIPM_ab_a4" ("\\U+041D\\U+041E\\U+041C\\U+0418\\U+041D\\U+0410\\U+041B" . "{R}"))
("GIPM_ab_dif" ("\\U+041D\\U+041E\\U+041C\\U+0418\\U+041D\\U+0410\\U+041B" . "{R}") ("\\U+0422\\U+041E\\U+041A\\U+0423\\U+0422\\U+0415\\U+0427\\U+041A\\U+0418" . "{M}"))
("GIPM_ab_dif4" ("\\U+041D\\U+041E\\U+041C\\U+0418\\U+041D\\U+0410\\U+041B" . "{R}") ("\\U+0422\\U+041E\\U+041A\\U+0423\\U+0422\\U+0415\\U+0427\\U+041A\\U+0418" . "{M}"))
("GIPM_ab_rcd2" ("\\U+0422\\U+041E\\U+041A\\U+0423\\U+0422\\U+0415\\U+0427\\U+041A\\U+0418" . "{M}") ("\\U+041D\\U+041E\\U+041C\\U+0418\\U+041D\\U+0410\\U+041B" . "{R}"))
("GIPM_ab_rcd4" ("\\U+041D\\U+041E\\U+041C\\U+0418\\U+041D\\U+0410\\U+041B" . "{R}") ("\\U+0422\\U+041E\\U+041A\\U+0423\\U+0422\\U+0415\\U+0427\\U+041A\\U+0418" . "{M}"))
("GIPM_ab_fire2" ("\\U+0422\\U+041E\\U+041A\\U+0423\\U+0422\\U+0415\\U+0427\\U+041A\\U+0418" . "{M}") ("\\U+041D\\U+041E\\U+041C\\U+0418\\U+041D\\U+0410\\U+041B" . "{R}"))
("GIPM_ab_fire4" ("\\U+041D\\U+041E\\U+041C\\U+0418\\U+041D\\U+0410\\U+041B" . "{R}") ("\\U+0422\\U+041E\\U+041A\\U+0423\\U+0422\\U+0415\\U+0427\\U+041A\\U+0418" . "{M}"))
("GIPM_ch_a1" ("\\U+041D\\U+041E\\U+041C\\U+0418\\U+041D\\U+0410\\U+041B" . "NXB-63 {R}"))
("GIPM_ch_a2" ("\\U+041D\\U+041E\\U+041C\\U+0418\\U+041D\\U+0410\\U+041B" . "NXB-63 {R}"))
("GIPM_ch_a3" ("\\U+041D\\U+041E\\U+041C\\U+0418\\U+041D\\U+0410\\U+041B" . "NXB-63 {R}"))
("GIPM_ch_a4" ("\\U+041D\\U+041E\\U+041C\\U+0418\\U+041D\\U+0410\\U+041B" . "NXB-63 {R}"))
("GIPM_ch_rcd2" ("\\U+041D\\U+041E\\U+041C\\U+0418\\U+041D\\U+0410\\U+041B" . "NXL-63 {R} I\\U+2206n{M}"))
("GIPM_ch_rcd4" ("\\U+041D\\U+041E\\U+041C\\U+0418\\U+041D\\U+0410\\U+041B" . "NXL-63 {R} I\\U+2206n{M}"))
("GIPM_rel_vip" )
("GIPM_G_iek_in_2" ("\\U+041D\\U+041E\\U+041C\\U+0418\\U+041D\\U+0410\\U+041B" . "C{I}"))
("GIPM_G_iek_in_3" ("\\U+041D\\U+041E\\U+041C\\U+0418\\U+041D\\U+0410\\U+041B" . "C{I}"))
("GIPM_G_iek_in_4" ("\\U+041D\\U+041E\\U+041C\\U+0418\\U+041D\\U+0410\\U+041B" . "C{I}"))
("GIPM_G_iek_a1_1" ("\\U+041D\\U+041E\\U+041C\\U+0418\\U+041D\\U+0410\\U+041B" . "C{I}"))
("GIPM_G_iek_a3_3" ("\\U+041D\\U+041E\\U+041C\\U+0418\\U+041D\\U+0410\\U+041B" . "C{I}"))
("GIPM_G_iek_dif_2" ("\\U+041D\\U+041E\\U+041C\\U+0418\\U+041D\\U+0410\\U+041B" . "C{I}"))
("GIPM_G_iek_dif4_4" ("\\U+041D\\U+041E\\U+041C\\U+0418\\U+041D\\U+0410\\U+041B" . "C{I}"))
("GIPM_G_iek_rcd_2" ("\\U+041D\\U+041E\\U+041C\\U+0418\\U+041D\\U+0410\\U+041B" . "{I}A"))
("GIPM_G_iek_fire_2" ("\\U+041D\\U+041E\\U+041C\\U+0418\\U+041D\\U+0410\\U+041B" . "{I}A"))
("GIPM_G_iek_fire_4" ("\\U+041D\\U+041E\\U+041C\\U+0418\\U+041D\\U+0410\\U+041B" . "{I}A"))
("GIPM_G_abb_in_2" ("\\U+041D\\U+041E\\U+041C\\U+0418\\U+041D\\U+0410\\U+041B" . "C{I}"))
("GIPM_G_abb_in_3" ("\\U+041D\\U+041E\\U+041C\\U+0418\\U+041D\\U+0410\\U+041B" . "C{I}"))
("GIPM_G_abb_in_4" ("\\U+041D\\U+041E\\U+041C\\U+0418\\U+041D\\U+0410\\U+041B" . "C{I}"))
("GIPM_G_abb_a1_1" ("\\U+041D\\U+041E\\U+041C\\U+0418\\U+041D\\U+0410\\U+041B" . "C{I}"))
("GIPM_G_abb_a3_3" ("\\U+041D\\U+041E\\U+041C\\U+0418\\U+041D\\U+0410\\U+041B" . "C{I}"))
("GIPM_G_abb_dif_2" ("\\U+041D\\U+041E\\U+041C\\U+0418\\U+041D\\U+0410\\U+041B" . "C{I}"))
("GIPM_G_abb_dif4_4" ("\\U+041D\\U+041E\\U+041C\\U+0418\\U+041D\\U+0410\\U+041B" . "C{I}"))
("GIPM_G_abb_rcd_2" ("\\U+041D\\U+041E\\U+041C\\U+0418\\U+041D\\U+0410\\U+041B" . "{I}A"))
("GIPM_G_abb_fire_2" ("\\U+041D\\U+041E\\U+041C\\U+0418\\U+041D\\U+0410\\U+041B" . "{I}A"))
("GIPM_G_abb_fire_4" ("\\U+041D\\U+041E\\U+041C\\U+0418\\U+041D\\U+0410\\U+041B" . "{I}A"))
("GIPM_G_dekraft_in_2" ("\\U+041D\\U+041E\\U+041C\\U+0418\\U+041D\\U+0410\\U+041B" . "C{I}"))
("GIPM_G_dekraft_in_3" ("\\U+041D\\U+041E\\U+041C\\U+0418\\U+041D\\U+0410\\U+041B" . "C{I}"))
("GIPM_G_dekraft_in_4" ("\\U+041D\\U+041E\\U+041C\\U+0418\\U+041D\\U+0410\\U+041B" . "C{I}"))
("GIPM_G_dekraft_a1_1" ("\\U+041D\\U+041E\\U+041C\\U+0418\\U+041D\\U+0410\\U+041B" . "C{I}"))
("GIPM_G_dekraft_a3_3" ("\\U+041D\\U+041E\\U+041C\\U+0418\\U+041D\\U+0410\\U+041B" . "C{I}"))
("GIPM_G_dekraft_dif_2" ("\\U+041D\\U+041E\\U+041C\\U+0418\\U+041D\\U+0410\\U+041B" . "C{I}"))
("GIPM_G_dekraft_dif4_4" ("\\U+041D\\U+041E\\U+041C\\U+0418\\U+041D\\U+0410\\U+041B" . "C{I}"))
("GIPM_G_dekraft_rcd_2" ("\\U+041D\\U+041E\\U+041C\\U+0418\\U+041D\\U+0410\\U+041B" . "{I}A"))
("GIPM_G_dekraft_fire_2" ("\\U+041D\\U+041E\\U+041C\\U+0418\\U+041D\\U+0410\\U+041B" . "{I}A"))
("GIPM_G_dekraft_fire_4" ("\\U+041D\\U+041E\\U+041C\\U+0418\\U+041D\\U+0410\\U+041B" . "{I}A"))
("GIPM_G_chint_in_2" ("\\U+041D\\U+041E\\U+041C\\U+0418\\U+041D\\U+0410\\U+041B" . "C{I}"))
("GIPM_G_chint_in_3" ("\\U+041D\\U+041E\\U+041C\\U+0418\\U+041D\\U+0410\\U+041B" . "C{I}"))
("GIPM_G_chint_in_4" ("\\U+041D\\U+041E\\U+041C\\U+0418\\U+041D\\U+0410\\U+041B" . "C{I}"))
("GIPM_G_chint_a1_1" ("\\U+041D\\U+041E\\U+041C\\U+0418\\U+041D\\U+0410\\U+041B" . "C{I}"))
("GIPM_G_chint_a3_3" ("\\U+041D\\U+041E\\U+041C\\U+0418\\U+041D\\U+0410\\U+041B" . "C{I}"))
("GIPM_G_chint_dif_2" ("\\U+041D\\U+041E\\U+041C\\U+0418\\U+041D\\U+0410\\U+041B" . "C{I}"))
("GIPM_G_chint_dif4_4" ("\\U+041D\\U+041E\\U+041C\\U+0418\\U+041D\\U+0410\\U+041B" . "C{I}"))
("GIPM_G_chint_rcd_2" ("\\U+041D\\U+041E\\U+041C\\U+0418\\U+041D\\U+0410\\U+041B" . "{I}A"))
("GIPM_G_chint_fire_2" ("\\U+041D\\U+041E\\U+041C\\U+0418\\U+041D\\U+0410\\U+041B" . "{I}A"))
("GIPM_G_chint_fire_4" ("\\U+041D\\U+041E\\U+041C\\U+0418\\U+041D\\U+0410\\U+041B" . "{I}A"))
("GIPM_G_xb_3" )
("GIPM_G_xb_5" )
))))

(gip:on-load)
(princ)
